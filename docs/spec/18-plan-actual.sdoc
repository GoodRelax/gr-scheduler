[DOCUMENT]
TITLE: gr-scheduler 要求仕様 - 予実管理 (L1-L3)

[GRAMMAR]
IMPORT_FROM_FILE: gr-scheduler-grammar.sgra

[TEXT]
STATEMENT: >>>
本書は gr-scheduler の予実管理ドメイン (プレフィクス PLAN) のシステム要求 (L1) と
コンポーネント要求 (L2) を定義する。予定と実績の区別・表示切替 (予定のみ/実績のみ/両方)・
イナズマ線 (progress line) によるボトルネック可視化・変更前予定 (ベースライン) の
別ファイル参照によるグレー表示を扱う。各 L1 要求はステークホルダ要求 STK-L0-011
(予実管理と遅れの可視化) を Parent で詳細化する。出典は `user-order.md` item54-57 と
`01-stakeholder-requirements.sdoc`。

予実の持ち方は CR-001 (承認 2026-07-19) で実績日フィールド方式へ移行した。実績を別アイテム
ではなく同一アイテムの実績日フィールド (actualStart / actualEnd) として保持し、旧方式の
planActualKind / planGroupId は廃止する。進捗率のみの方式では実績の時間ズレ (着手遅れ・
期間変動) を表現できず日本の予実文化に不足するため採らない。実績日フィールド方式は MSPDI の
Baseline / Actual / PercentComplete とも素直に往復する。表示は同一データからの描画切替として
Overlap (重ね塗り・既定) と Separate (分離) の 2 スタイルを提供する (viewState.planActualStyle)。
予実の配色はアイテムのベース色 (fillColor) 1 色から彩度で導出し (PLAN-L1-006)、変更前予定は
別ファイル参照方式のグレー・アンダーレイで示す (PLAN-L1-004、CR-002)。
データ形式契約は `40-data-format.sdoc`、依存の linkType / lagDays は `16-dependencies.sdoc`、
期限マーカー targetDate は `11-items-icons.sdoc` を参照する。
<<<

[[SECTION]]
TITLE: 1. 予定と実績の区別 (Plan vs Actual)

[REQUIREMENT]
UID: PLAN-L1-001
TYPE: Functional
PRIORITY: Must
LAYER: L1_System
TITLE: 予定と実績を同一アイテムの実績日フィールドで区別して管理する
STATEMENT: >>>
本システムは、各マイルストーン/タスクについて、予定スパンを startDate / endDate として
保持し、実績を同一アイテム上の実績日フィールド actualStart / actualEnd (任意。マイルストーンは
actualEnd を null) として保持することで、実績を別アイテムに分けずに予定と実績を 1 つの
アイテムで区別・管理できること。旧来の planActualKind / planGroupId 方式は廃止する。
<<<
RATIONALE: >>>
実績を「別アイテム」ではなく「同一アイテムの実績日フィールド」で持つ方式 (CR-001) を採る。
進捗率のみでは着手遅れ・期間変動という実績の時間ズレを表せず日本の予実文化に不足する。
同一アイテム上に予定スパンと実績日を並置することが遅れ把握の前提であり、予実区別は
プロパティ (STK-L0-007) と整合する。actualStart / actualEnd は MSPDI の
ActualStart / ActualFinish と往復する。user-order item54、CR-001 Part A。
<<<
VERIFICATION: >>>
1 つのアイテムに予定日 (startDate / endDate) と実績日 (actualStart / actualEnd) を入力でき、
別アイテムを作らずに同一アイテム上で予定表現と実績表現が区別して描画されること。
planActualKind / planGroupId が廃止され、データに残らないこと。
<<<
RELATIONS:
- TYPE: Parent
  VALUE: STK-L0-011

[[/SECTION]]

[[SECTION]]
TITLE: 2. 予実の表示切替 (Plan / Actual / Both)

[REQUIREMENT]
UID: PLAN-L1-002
TYPE: Functional
PRIORITY: Must
LAYER: L1_System
TITLE: 予定のみ/実績のみ/両方の表示を切り替える
STATEMENT: >>>
本システムは、予実の表示状態を予定のみ・実績のみ・予定と実績の両方・非表示の状態から選んで
切り替えられ (viewState.planActualDisplay = 'plan-only' | 'actual-only' | 'both' | 'none')、
選択した状態に応じて該当する要素のみをキャンバスへ描画すること。この可視フィルタは、予定/
実績の描き方を決める表示スタイル (viewState.planActualStyle、PLAN-L1-005) とは独立とする。
<<<
RATIONALE: >>>
計画レビューでは予定のみ、進捗確認では実績のみ、差分確認では両方、と用途で見せ方を
変える。planActualDisplay は「何を見せるか」の可視フィルタであり、「どう重ねて/分けて描くか」の
planActualStyle (Overlap / Separate) とは役割が異なる。user-order item55、CR-001 Part A。
<<<
VERIFICATION: >>>
表示状態を予定のみに切り替えると実績が非表示、実績のみで予定が非表示、両方で双方が
表示されること。
<<<
RELATIONS:
- TYPE: Parent
  VALUE: STK-L0-011

[[/SECTION]]

[[SECTION]]
TITLE: 3. イナズマ線 (Progress Line)

[REQUIREMENT]
UID: PLAN-L1-003
TYPE: Functional
PRIORITY: Must
LAYER: L1_System
TITLE: 実績表示でイナズマ線を引く
STATEMENT: >>>
本システムは、実績を表示する場面で、基準日 (例: 本日) を起点に各行の実績進捗位置を
順に結ぶイナズマ線 (progress line) を引け、線の折れによってどの行が遅れ/進みか
(ボトルネック) を可視化できること。イナズマ線の表示/非表示は、フローティングパレット上の
専用トグル (カーソルボタンの右) で切り替えられ (viewState.progressLineVisible)、その既定値は
非表示とすること。すなわち新規文書ではイナズマ線を描画せず、ユーザーがパレットのトグルで
表示に切り替えたときにのみ描画すること。
<<<
RATIONALE: >>>
基準日で各行の進捗を折れ線状に結ぶと、基準日より左へ凹む行が遅れ、右へ出る行が先行と
一目で分かる。ボトルネックの発見に直結する。イナズマ線の頂点算出は PLAN-L2-001 で
定義する。user-order item56。イナズマ線は常時表示だと一枚絵が煩雑になるため、パレットの
表示/非表示トグルを設け既定を非表示へ改める (旧既定=表示から変更)。データ既定値
(progressLineVisible) の具体差分は 40-data-format.sdoc に橋渡しする。CR-006 Part 5。
<<<
VERIFICATION: >>>
新規文書ではイナズマ線が既定で非表示であること (viewState.progressLineVisible の既定=非表示)。
パレットのカーソルボタン右のトグルで表示へ切り替えると、実績表示で基準日を指定した際に
イナズマ線が各行の実績進捗位置を結んで描画され、遅れている行で基準日より進捗側 (過去側) へ
折れることが視認でき、再度トグルで非表示へ戻せることを確認すること。
<<<
RELATIONS:
- TYPE: Parent
  VALUE: STK-L0-011

[REQUIREMENT]
UID: PLAN-L2-001
TYPE: Non-Functional
PRIORITY: Should
LAYER: L2_Component
TITLE: イナズマ線レンダラの頂点算出 (統一 front 規則)
STATEMENT: >>>
イナズマ線レンダラは、基準日と各アイテムの実績日/進捗率から行ごとの到達点 (front) を
次の統一規則で算出し、基準日の縦位置を軸に隣接行の頂点を順に結ぶ折れ線の頂点列を
生成すること。以下の 4 ケースは MECE (相互排他かつ網羅的) であり、任意のアイテムは
必ず 1 ケースに該当する。
(1) actualStart と actualEnd の双方あり (完了実績): front = actualStart + progressRatio ×
(actualEnd − actualStart)。
(2) actualStart あり・actualEnd なし (進行中): front = actualStart + progressRatio ×
(endDate − actualStart) (Formula A)。
(3) actualStart なし・かつ progressRatio > 0 (実績日なし・予定上で進捗あり): front =
startDate + progressRatio × (endDate − startDate) (MSP の PercentComplete 相当)。
(4) actualStart なし・かつ (progressRatio が無い または = 0) (未着手): 頂点を出さない。
ケース (3) と (4) の境界は progressRatio > 0 で厳密に切り、progressRatio が存在しても
0 の場合は必ず (4) に属する (present-but-zero を (4) 側へ確定させる)。
進行中 (ケース 2) は endDate を暫定の実績終了とみなす線形補間で、遅れ開始が頂点を右へ押す。
エッジ: endDate ≤ actualStart のとき span が退化するため front = actualStart にクランプする。
なお、幅 0 のマイルストーン (milestoneShape、区間を持たない) は上記 4 ケースのスパン補間が
退化するため特例とする: マイルストーンの front は「点」とし、実績があれば actualStart、
無ければ startDate とする (補間しない)。
<<<
RATIONALE: >>>
イナズマ線 (PLAN-L1-003) の内部描画ロジックを実績日フィールド方式 (CR-001 Part A) の
統一 front 規則で規定する。実績日がある行は実績スパン上で、無い行は予定スパン上で到達位置を
求めることで、同一アイテムモデルから実績あり/なし両ケースを一貫して扱える。行の並び順に頂点を
並べ、基準日に一致する行は軸上、遅れ行は過去側、先行行は未来側へ頂点を置くことで折れの
向きが遅れ/進みを表す。user-order item56、CR-001 Part A。
<<<
VERIFICATION: >>>
4 ケースを網羅する既知データを入力に頂点列を算出し、(1) 完了実績 (actualStart と actualEnd
双方あり) の行が actualStart..actualEnd 上の front に、(2) 進行中 (actualStart あり・actualEnd
なし) の行が actualStart..endDate 上の front (Formula A) に、(3) 実績日なし・かつ
progressRatio > 0 の行が startDate..endDate 上の front に頂点を置き、(4) 未着手 (actualStart
なし・かつ progressRatio が無い または = 0) の行は頂点を出さないことを単体テストで確認すること。
とくに progressRatio が存在しても = 0 の行が (3) ではなく (4) に判定され頂点を出さないことを
境界値として確認すること。加えて進行中でエッジ (endDate ≤
actualStart) の入力に対し front が actualStart にクランプされること、遅れ行の頂点が基準日軸
より過去側・先行行が未来側・定時行が軸上に置かれることを確認すること。さらに、幅 0 の
マイルストーンの入力に対し front が「点」として算出され、実績あり (actualStart) の行は
actualStart、実績なしの行は startDate に頂点を置き、スパン補間されないことを確認すること。
<<<
RELATIONS:
- TYPE: Parent
  VALUE: PLAN-L1-003

[[/SECTION]]

[[SECTION]]
TITLE: 4. 変更前予定 (ベースライン) の別ファイル参照グレー表示

[REQUIREMENT]
UID: PLAN-L1-004
TYPE: Functional
PRIORITY: Must
LAYER: L1_System
TITLE: 変更前の予定をベースライン別ファイル参照でグレー表示して計画変更を可視化する
STATEMENT: >>>
本システムは、変更前の予定 (ベースライン) を現行データとは別ファイル (過去予定スナップショット、
JSON のみ。MSPDI XML は不可) として読み込み、対象行と同じ高さに薄いグレー・編集不可の
アンダーレイとして描画することで、計画がどう動いたか (計画変更) を可視化できること。
ベースライン参照ファイルは Load 時のオプションで「ベースライン扱い」であることを明示指定して
読み込み (通常の編集対象としての Load とは区別する)、現行アイテムとの対応付けは id をキーに
突合する。参照ファイル内の実績は無視し予定日のみを用いる。ベースライン層の表示/非表示は
ヘッダーに配置する専用トグル (Visible / Invisible) で切り替え、予実の可視フィルタ
(planActualDisplay、PLAN-L1-002) とは独立とする。旧 item.previousPlan フィールドは廃止する。
<<<
RATIONALE: >>>
現行の予定だけでは「いつどれだけ計画が動いたか」が見えない。変更前をグレーで残すことで
計画変更の履歴を一枚絵の上に示す。ベースラインを per-item の previousPlan フィールドで持つと
入力負担が大きく、フィールドとファイルの二重管理 (SSOT 違反) になるため、別ファイル参照方式
へ改めた。描画は対象行と同じ高さ (オフセットしない) とし、行内の上下位置・サイズは現行
アイテムのレイアウト結果に一致させる。MSPDI Baseline (BaselineStart / BaselineFinish) は
参照文書の id 突合で best-effort 往復する。user-order item57、CR-002 (CR-001 Part A の
previousPlan 据え置きと Part B-4 の Baseline clean 往復を supersede)。
<<<
VERIFICATION: >>>
過去予定スナップショット (JSON) を「ベースライン扱い」オプション付きで Load すると、対象行と
同じ高さに薄いグレー・編集不可のアンダーレイが id 突合で描画され、現行アイテムとの差分
(計画の移動) が視認できること。ヘッダーの専用トグル (Visible / Invisible) で当該層の表示/
非表示が planActualDisplay とは独立に切り替わること。item.previousPlan フィールドが廃止され、
データに残らないこと。
<<<
RELATIONS:
- TYPE: Parent
  VALUE: STK-L0-011

[[/SECTION]]

[[SECTION]]
TITLE: 5. 予実の表示スタイル (Overlap / Separate)

[REQUIREMENT]
UID: PLAN-L1-005
TYPE: Functional
PRIORITY: Must
LAYER: L1_System
TITLE: 予実の描画スタイルを重ね塗り/分離で切り替える
STATEMENT: >>>
本システムは、同一アイテムの予定スパン (startDate / endDate) と実績日 (actualStart /
actualEnd) を、viewState.planActualStyle により 2 つの描画スタイルで切り替えて表示できること。
Overlap (重ね塗り、既定) では予定バーの上に実績/進捗を塗り重ねる。Separate (分離) では
予定バーと実績バー (actualStart..actualEnd) を上下に分けて描く。いずれも同一データからの
描画切替であり、データ設計とは独立とする。既定値は Overlap とする。Overlap / Separate の
切替は、フローティングパレット上の専用トグル ``[Ao]`` (Overlap) / ``[As]`` (Separate) で行い、
既定選択は ``[Ao]`` (Overlap) とする。本トグルは UI 操作面の追加であり、viewState.planActualStyle
のデータ設計・既定値 (overlap) は変更しない。

Separate における上下配置は、バー高ではなく行 (レーン帯) の高さで確保すること。すなわち:

規則 (1) タスクバーの高さは Overlap 表示時と同じ通常の高さを維持し、予定バー・実績バーのいずれも
半分の高さへ縮めないこと (レーン高を上下 2 分割する旧規則は本規定が supersede する)。

規則 (2) その代わり、実績バーを予定バーの下へ積むレーンについて、行 (レーン帯) の高さが
予定バー 1 段 + 区切りの余白 + 実績バー 1 段を収めるのに必要な分だけ伸びること。伸長は
レーン単位で加算し、実績バーを積むレーンの本数ぶんだけ行高が増えること。1 行に時間的に重なる
複数アイテムがある既存のレーン積み上げと併発しても、両者が破綻なく (重ならず) 表示されること。

規則 (3) 伸長の対象は、実績バーが実際に描かれるレーンに限ること。すなわち planActualStyle が
separate であり、かつ可視フィルタ (planActualDisplay、PLAN-L1-002) が予定側と実績側の双方を
表示しており、かつ当該アイテムが実績バーを描く場合にのみ、そのレーンが追加の高さを確保する。
plan-only / actual-only では単一のバーがレーンを満たすため、また overlap では上下に積まないため、
追加の高さを一切確保しないこと。実績を持たないアイテムのみで構成される行は、 ``[As]`` へ
切り替えても高さが変化しないこと。

規則 (4) 行が確保する追加の高さと、幾何が実績バーを置く縦オフセットは同一の定義から導くこと
(行高と描画位置が二重定義により乖離しないこと)。左ペイン分類ツリーの行高も、伸びたキャンバス行の
高さと一致し続けること。
<<<
RATIONALE: >>>
実績日フィールド方式 (CR-001 Part A) では実績を同一アイテムの実績日で持つため、同じデータから重ね塗りと
分離の双方を描ける。用途に応じて、コンパクトな重ね塗り (既定) と、予定/実績を並置して
ズレを強調する分離を選べるようにする。実装名は Overlap / Separate を用い、Opt1 / Opt2 の
呼称は使わない。planActualStyle は描き方を決めるスタイルであり、可視フィルタの
planActualDisplay (PLAN-L1-002) とは独立とする。CR-001 Part A。Overlap / Separate を
パレットの ``[Ao]`` / ``[As]`` トグルで切り替える UI を新設する (既定 ``[Ao]`` = Overlap は
据え置き、データモデルは不変)。CR-006 Part 6。
Separate でバー高を半分にする旧規則は、通常 18px のバーが 8px 前後まで縮み視認性を大きく損ねる
ことがライブ視覚レビューで判明したため廃する。ユーザーの期待は「バーはそのまま、行が伸びる」で
あり、これは 1 行に時間重複するアイテムを積むときに行バンドを伸ばす既存の考え方 (レーン積み上げ)
と同じ解法である。伸長を実績バーを描くレーンだけに限るのは、実績を持たない行が
Separate へ切り替えただけで無駄に高さを消費し、一枚絵の俯瞰性 (STK-L0-011) を損なうのを避ける
ためである。行高の決定はレンダラではなくレイアウトエンジン (ドメイン) の責務とし、行が確保する
高さと幾何が描く位置を同一定義から導くことで両者の乖離を構造的に不能にする。CR-013 Part 1。
<<<
VERIFICATION: >>>
実績日を持つ同一アイテム集合に対し、viewState.planActualStyle を overlap にすると予定バー上へ
実績/進捗が重ね塗りされ、separate にすると予定バーと実績バーが上下に分離して描かれること。
既定 (未指定) では Overlap で描かれること。パレットの ``[Ao]`` / ``[As]`` トグルで overlap /
separate が切り替わり、既定選択が ``[Ao]`` (Overlap) であること。両描画が同一データから得られる
こと。
加えて Separate の行高規則として、(a) separate 時の予定バー・実績バーの高さが overlap 時の
バー高と同一であること (半分にならないこと)、(b) 実績バーを積むレーンを持つ行のみ行高が
1 レーンあたり一定量だけ増え、実績を持たない行・overlap・plan-only・actual-only の行高が
変化しないこと、(c) 時間重複によるレーン積み上げと併発した行で、上段レーンの実績バー下端が
下段レーンの上端を侵さないこと、(d) 実績を積むレーンが 1 本だけの行では行高の増分も 1 レーン分に
留まること、(e) 左ペイン分類ツリーの行高がキャンバス行の高さと一致し続けることを確認すること。
<<<
RELATIONS:
- TYPE: Parent
  VALUE: STK-L0-011

[REQUIREMENT]
UID: PLAN-L2-002
TYPE: Functional
PRIORITY: Must
LAYER: L2_Component
TITLE: 実績バーの最小記録・最小描画幅・実績ドラッグ操作 (ズーム非依存・掴み代・作用域)
STATEMENT: >>>
実績を新規に記録した直後のタスクバーと、実績バーを起点とするドラッグ操作について、次を
満たすこと。 Overlap / Separate のいずれのスタイルでも共通とする。

規則 (1) 最小の実績記録: 実績を新規に記録する操作は actualStart のみを設定し、actualEnd は
未設定 (null) のままとすること。 actualStart の既定値は当該アイテムの予定 startDate とする。
この状態は「着手済み・未完了 (進行中)」であり、PLAN-L2-001 の 4 ケース MECE 規則のケース (2)
に既に定義済みの状態である (新しいケースを追加するものではない)。架空の終了日を
書き込まないこと。

規則 (2) 最小描画幅と掴み代: 実績バーは、スクリーン座標系 (画面ピクセル) で一定の最小描画幅・
最小ヒット領域 (目安 12px、標準的なマウスカーソル幅の概ね 3/4) を、現在のズーム倍率に
かかわらず保つこと。これにより継続期間ゼロ (actualStart のみ) の実績バーも常に視認でき、
マウスで掴めること。描画する矩形と当たり判定の矩形は同一の定義から導き、見えている図形と
掴める領域が一致すること。
ただし予定バーを実績バーと並べて描く場合 (可視フィルタ planActualDisplay が予定側と実績側の
双方を表示する場合) は、この最小幅による右端の張り出しを予定バーの右端でクランプすること。
クランプは、記録された実績終了が予定終了を越えていないときに限り適用し、退化した (継続期間
ゼロの) 実績が予定超過として読めてしまうことを防ぐ。記録された実績終了自体が予定終了を越える
真の超過ではクランプせず、実績バーの全長をそのまま描くこと。またクランプが実績の記録済み
右端より手前へバーを引き戻すことはない。予定バーを並べて描かない実績のみ表示 (actual-only)
では、誤読の対象となる予定バーが存在せず、最小幅だけが実績の視認性と掴みやすさを担保するため、
クランプを適用しないこと。

規則 (3) ズーム非依存: 最小幅の確保は描画時のみに適用し、記録される日付を一切変更しないこと。
ピクセル幅から日数を逆算して実績日を書き込んではならない。同一の実績記録操作を異なるズーム
倍率で行っても、記録される actualStart / actualEnd が同一であること。

規則 (4) 掴みの作用域と実績ドラッグ操作: 実績バーを起点とする掴み (ドラッグ) は、実績スパン
(actualStart / actualEnd) にのみ作用し、予定日 (startDate / endDate) を決して書き換えないこと。
タスクバーの実績側ドラッグは次の 3 操作とし、いずれも Undo 可能なコマンドとして発行して
Undo で操作前の実績日へ、Redo で操作後の実績日へ戻せること (TOOL-L1-004)。

操作 (1) 右辺のドラッグ: actualEnd を書き込む。actualEnd が未記録 (null) のタスクでは、最初の
右辺ドラッグが actualEnd を null から実日付へ確定させる。このとき基準とする日付は規則 (1) の
退化スパン、すなわち当該実績の actualStart とし、結果は actualStart 以上へクランプする
(同日終了は正当な実績として許す)。

操作 (2) 左辺のドラッグ: actualStart を書き込む。actualEnd が記録済みの場合は、結果を
actualEnd 以下へクランプする (actualEnd が未記録の場合はクランプの対象が無い)。

操作 (3) 本体のドラッグ: 記録済みの実績スパン全体を平行移動する。actualStart と actualEnd の
双方を同じ日数だけずらし、記録された実績期間 (継続日数) を保つこと。actualEnd が未記録の
場合は actualStart のみを移動する。

操作 (1) から操作 (3) のいずれも、予定日 (startDate / endDate) を変更しないこと (本規則の
作用域を再確認する)。

適用範囲: 操作 (1) から操作 (3) は、実績側の掴み対象が実在するアイテムに適用する。予定側と
実績側の双方を表示している状態 (both) でこれに該当するのは、実績を記録した矩形のタスクバー、
すなわち独立した実績バーを描くアイテムに限る。パス形状のタスク字形 (矢印・シェブロン・スパン)
と両端テーパ (フェード) を持つタスクは単一の字形として描かれ、独立した実績バーを持たないため、
この状態では実績側に掴める矩形が存在せず、操作 (1) から操作 (3) を行えない。これらのアイテムの
掴みは予定バーとして予定日に作用し、実績日はプロパティパネルからの編集で変更する。一方、
実績のみ表示 (actual-only) では、描かれる唯一の字形が実績そのものであるため、字形によらず
操作 (1) から操作 (3) が実績日に作用する。

規則 (5) マイルストーンの実績: 区間を持たないマイルストーンの実績は actualStart の点マーカーで
あり (PLAN-L1-007)、幅の概念もリサイズ可能な辺も持たない。したがって規則 (2) の最小描画幅と
操作 (1) / 操作 (2) の辺ドラッグは適用しない。掴み対象としても、予定側と実績側の双方を表示して
いる状態 (both) では実績マーカーは独立した掴み対象ではなく、その位置での掴みは予定の字形に
解決される (予定日に作用する)。実績マーカーが唯一の掴み対象となるのは実績のみ表示
(actual-only) であり、この状態でマイルストーンの実績を掴んだドラッグは actualStart のみを
動かすこと (actualEnd は null のまま、辺によるリサイズは起こらない)。規則 (2) と規則 (3) の
対象はタスクバーに限る。

規則 (6) 最小幅の帰結 (本体領域を持たないこと): 辺のリサイズ掴み代は片側あたり一定の
スクリーンピクセル (目安 9px) であり、左右の掴み代はバー幅の半分を上限にクランプされて互いに
重ならないこと。その結果、規則 (2) の最小幅 (12px) で描かれた新規実績バーは左右の掴み代
2 つだけで占められ、本体 (body) 領域を持たない。すなわち新規実績バーの左半分は操作 (2)
(開始のリサイズ)、右半分は操作 (1) (終了のリサイズ) に解決され、平行移動 (操作 (3)) は
実績スパンが掴み代 2 つ分より広くなってから可能となること。
<<<
RATIONALE: >>>
実績を初めて記録した直後の実績はスパンが退化する (actualStart のみ) ため、素直に描くと幅ゼロ
となり、ユーザーが最初に行いたい「実績バーを掴んで実際の終了日を決める」操作ができない。
これを日付側で埋める (ピクセルから逆算した終了日を書き込む) と、記録される日付が操作時の
ズーム倍率に依存し同じ操作でも結果が変わる (再現性が無い) ため採らない。最小幅の保証を
レンダラ (表示専用の関心事) に閉じることで、データは常にズームから独立し、ユーザーが実際に
確定した値のみを保つ。描画矩形と掴み矩形を同一定義から導くのは、見えている図形と掴める領域が
ずれるのが最も分かりにくい誤操作の原因になるためである。掴みの作用域を実績側に限るのは、
実績バーを掴んだのに予定日が動くという最小驚きの原則 (POLA) 違反を防ぐためであり、とくに
実績のみ表示では予定バーが描かれず変化に気付けないため必須である。PLAN-L1-005 の描画スタイルを
実績バーの最小表現の観点から詳細化する。CR-013 Part 2。
規則 (4) の 3 操作 (右辺・左辺・本体のドラッグ) は CR-013 Part 2 が受入基準として求めた実績側の
身振りであり、実装されたため要求として明文化する (仕様に無いまま実装だけが存在する状態を
残さない)。右辺ドラッグを「未記録の actualEnd を実日付へ確定させる唯一の身振り」と定めるのは、
規則 (1) が架空の終了日を書かないと決めた結果、ユーザーが最初に行う操作が「実績バーの右端を
掴んで実際の終了日まで引く」ことになるためである。その基準を actualStart に置くのは、退化スパン
では左右の端が一致しており、そこからの差分でしか終了日を導けないからである。左辺を actualEnd
以下、右辺を actualStart 以上へクランプするのは、実績の開始が終了を追い越す不整合な記録を
そもそも作れなくするためであり、同日 (継続 1 日未満) の実績は現実に起こるため禁止しない。
本体ドラッグで期間を保つのは「着手が丸ごとずれた」という実務上もっとも多い訂正を 1 操作で
表せるようにするためである。3 操作を Undo 可能とするのは、実績日が永続ドキュメント値であり
他の編集と同じ取り消し規約に従うべきだからである。
規則 (4) の適用範囲と規則 (5) の掴み対象の限定は、要求が実際より広く読めることを避けるための
明記である。実績側のドラッグは実績側の掴み矩形が存在して初めて成立し、その矩形は「独立した
実績バーを描くアイテム」にしか与えられない。パス形状の字形とフェード字形は 1 つの字形で
アイテム全体を表すため実績バーを別に描かず、マイルストーンは点であり、いずれも双方表示では
実績側の掴み対象を持たない。ここで身振りが使えるかのように書くと、仕様と実装の乖離を
逆向きに作り込むことになる。実績のみ表示で身振りが成立するのは、その状態では描かれる唯一の
字形が実績そのものだからであり、字形の種類とは無関係である。
規則 (2) のクランプは、最小幅が描画上の補助にすぎないのに、短い予定バーや低い zoomX では
退化した実績が予定右端を越えて描かれ「実績が予定を超過した」と読めてしまうためである。データが
主張していない超過を絵が主張してはならない一方、記録された実績終了が本当に予定終了を越えている
場合は真の遅れであり、これを縮めると遅れの隠蔽になるためクランプしない。実績のみ表示では
比較対象の予定バーが画面に無く誤読が成立せず、最小幅は掴みやすさの唯一の担保となるため
クランプを外す。規則 (6) は掴み代と最小幅の寸法関係から導かれる帰結であり、新規実績バーが
本体領域を持たないこと (左半分=開始・右半分=終了) を明示しておかないと、実装者やテスト設計者が
「新規実績を本体ドラッグで動かせるはず」という成立しない前提を置くためである。
<<<
VERIFICATION: >>>
実績を新規に記録した直後のアイテムが actualStart のみを持ち (actualEnd が未設定であること)、
actualStart が予定 startDate と一致することを確認すること。当該実績バーが、ズーム倍率を
変えても (縮小・等倍・拡大のいずれでも) スクリーン座標系で同一の最小描画幅を保ち、その矩形が
当たり判定の矩形と一致してマウスで掴めることを確認すること。同一の実績記録操作を異なるズーム
倍率で行い、記録される actualStart / actualEnd が同一であることを確認すること。実績バーを
起点とする掴みが startDate / endDate を変化させないこと、およびマイルストーンの 2 マーカー表示
(PLAN-L1-007) が本要求の影響を受けないことを確認すること。
加えて規則 (2) のクランプとして、(a) 予定側と実績側の双方を表示している状態で、記録された実績
終了が予定終了を越えていない (未記録を含む) 実績バーの右端が予定バーの右端を越えないこと、 (b)
記録された実績終了が予定終了を越える真の超過ではバーが縮められず全長で描かれること、 (c) 実績
のみ表示 (actual-only) ではクランプされず最小幅がそのまま保たれることを確認すること。
さらに規則 (4) の実績ドラッグとして、(d) actualEnd が未記録のタスクの右辺をドラッグすると
actualEnd が actualStart を基準とした実日付として記録され、actualStart より前へは決して
下がらないこと、(e) 左辺のドラッグが actualStart を書き換え、actualEnd が記録済みの場合は
actualEnd を越えないこと、(f) 本体のドラッグが actualStart と actualEnd を同じ日数だけ動かして
実績期間を保つこと (actualEnd が未記録なら actualStart のみ動くこと)、(g) これら 3 操作の
いずれもが Undo で操作前の実績日へ戻り Redo で再適用されること、(h) これら 3 操作の前後で
startDate / endDate が一切変化しないことを確認すること。加えて (i) 実績のみ表示において
マイルストーンの実績を起点とするドラッグが actualStart のみを動かし actualEnd が null のまま
であること (辺によるリサイズが起こらないこと)、(j) 最小幅で描かれた新規実績バーが本体領域を
持たず、左半分の掴みが開始のリサイズ・右半分の掴みが終了のリサイズに解決されることを確認する
こと。
さらに規則 (4) の適用範囲として、(k) 予定側と実績側の双方を表示している状態では、パス形状の
タスク字形・フェードを持つタスク・マイルストーンに実績側の掴み対象が存在せず、その位置での
掴みが実績日ではなく予定側の操作として解決されること、(l) 実績のみ表示ではこれらの字形でも
唯一描かれる字形が実績として掴め、タスクでは操作 (1) から操作 (3) が、マイルストーンでは
actualStart の移動のみが作用することを確認すること。
<<<
RELATIONS:
- TYPE: Parent
  VALUE: PLAN-L1-005

[REQUIREMENT]
UID: PLAN-L1-006
TYPE: Functional
PRIORITY: Must
LAYER: L1_System
TITLE: 予実の配色をベース色から彩度で導出し線幅を非色冗長符号とする
STATEMENT: >>>
本システムは、Overlap の予実塗り分けを、アイテムのベース色 (fillColor) 1 色から彩度で
導出すること: 予定は淡色 (desaturated/pale)、実績・進捗は濃色 (saturated/vivid) とし、
既定はこの淡 (予定)/濃 (実績) とする。色以外の冗長符号 (WCAG 1.4.1) は線の太さで表し、
予定線は細く (補足的)、実績線は太く描く (破線は用いない)。明示指定した fillColor
(fillColorExplicit) は優先し、ラベル可読性 (WCAG 1.4.3) を維持すること。旧来の固定
緑 (予定)/橙 (実績) の 2 色配色は廃止する。
<<<
RATIONALE: >>>
予定と実績を無関係な 2 色ではなくアイテムのベース色 1 色から彩度で導出すると、行ごとの
色分類を保ったまま予実を淡濃で表せる。非色の冗長符号は、破線が情報過多で見にくいという
ユーザー判断により線幅 (予定細/実績太) を採る。これにより色覚特性・グレースケール環境でも
予実を判別でき、WCAG 1.4.1 (色の使用) を満たす。CR-002 Part 1。
<<<
VERIFICATION: >>>
同一アイテムのベース色を変えると予定/実績塗りがその色の淡 (予定)/濃 (実績) として導出され、
グレースケール化しても予定線が細く実績線が太いことで両者を判別できること (破線を用いない)。
明示 fillColor 指定時もこの淡濃導出と線幅冗長符号が適用され、ラベルが可読であること。旧固定
緑/橙 2 色が用いられないこと。
<<<
RELATIONS:
- TYPE: Parent
  VALUE: STK-L0-011

[REQUIREMENT]
UID: PLAN-L1-007
TYPE: Functional
PRIORITY: Must
LAYER: L1_System
TITLE: マイルストーンの予実は2マーカーで描き区間を塗りつぶさない
STATEMENT: >>>
本システムは、幅 0 のマイルストーンの予実を、予定マーカー (startDate) と実績マーカー
(actualStart) の 2 点で描画し、両者の間を塗りつぶさない (区間が無いため塗り面を持たない)
こと。PLAN-L1-005 の Overlap / Separate による塗り分けは幅を持つタスクバーに適用され、
区間を持たないマイルストーンには適用しない。予定と実績のズレは 2 マーカーの水平距離と
イナズマ線頂点 (PLAN-L2-001) で表し、任意で 2 点間に細いリーダー線を引いてもよい。
マイルストーンは actualEnd を null とする。
<<<
RATIONALE: >>>
マイルストーンは区間を持たない「点」であり、タスクバー向けの区間塗り分け (Overlap /
Separate、PLAN-L1-005) をそのまま適用すると塗り面が定義できず表現が破綻する。予実の
ズレは点同士の水平距離とイナズマ線の折れで表すのが自然であり、実績日フィールド方式
(CR-001 Part A、マイルストーンは actualEnd を null) と整合する。イナズマ線側の頂点算出も
マイルストーンを点として扱う特例 (PLAN-L2-001) と一貫させる。user-order item54-56。
<<<
VERIFICATION: >>>
幅 0 のマイルストーンに予定日 (startDate) と実績日 (actualStart) を与えると、予定マーカーと
実績マーカーの 2 点が描画され、両者の間に塗り面 (区間) が生じないこと。planActualStyle を
overlap / separate のいずれにしてもマイルストーンには区間塗り分けが適用されず 2 マーカー
描画が維持されること。予実のズレが 2 マーカーの水平距離とイナズマ線頂点で視認でき、actualEnd
が null であることを確認すること。
<<<
RELATIONS:
- TYPE: Parent
  VALUE: STK-L0-011

[[/SECTION]]
