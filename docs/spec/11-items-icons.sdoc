[DOCUMENT]
TITLE: gr-scheduler 要求仕様 - アイテムとアイコン (L1-L3)

[GRAMMAR]
IMPORT_FROM_FILE: gr-scheduler-grammar.sgra

[TEXT]
STATEMENT: >>>
本書は gr-scheduler のマイルストーン/タスク (アイテム) とそのアイコンに関するシステム要求
(L1) を定義し、必要に応じてコンポーネント要求 (L2) へ詳細化する。各 L1 要求は Parent 関係で
ステークホルダ要求 STK-L0-006 (アイコンと図形・色・略称) および STK-L0-001 (マルチバー一枚絵の
俯瞰) をトレースする。ただし ITEM-L1-011 (期限マーカー) のみは例外で、STK-L0-011 (予実管理と
遅れの可視化) を Parent とする。出典は user-order.md item2, item7-11, item22, item23。
アイコン枠色/塗り色のパレット定義そのものは 12-properties-i18n.sdoc に、略称位置ドラッグの
座標同期は 13-layout-alignment.sdoc に主管を置く (重複回避)。なお外部画像 (SVG/PNG) の
アイコンインポートは CR-004 Part 6a で撤回した (旧 ITEM-L1-007 / ITEM-L1-008 / ITEM-L2-001。
撤去理由は当該 CR および 30-architecture.sdoc ARCH-C-026 を参照)。
<<<

[[SECTION]]
TITLE: 1. マルチバー配置 (Multi-bar Placement)

[REQUIREMENT]
UID: ITEM-L1-001
TYPE: Functional
PRIORITY: Must
LAYER: L1_System
TITLE: 1 行への複数アイテム配置
STATEMENT: >>>
gr-scheduler は、1 つの行 (帯) に複数のマイルストーン/タスクを、互いに重ならないように横並べ
して配置できること。
<<<
RATIONALE: >>>
マルチバー表示の中核をアイテム側の観点から規定する。既存ツールが持たない差別化点であり、
キャンバス面の描画は 10-canvas-view.sdoc が担う。user-order item2。
<<<
VERIFICATION: >>>
同一行に開始日の異なる 3 個以上のアイテムを配置したとき、いずれのアイコン矩形も他アイテムの
アイコン矩形と重ならず、各アイテムが独立に選択できること。
<<<
RELATIONS:
- TYPE: Parent
  VALUE: STK-L0-001

[[/SECTION]]

[[SECTION]]
TITLE: 2. 既定アイコンと図形 (Default Icons & Shapes)

[REQUIREMENT]
UID: ITEM-L1-002
TYPE: Functional
PRIORITY: Must
LAYER: L1_System
TITLE: 既定アイコンの提供
STATEMENT: >>>
gr-scheduler は、マイルストーンおよびタスクに対して、あらかじめ用意した既定のアイコン群を
提供し、ユーザーが選んで配置できること。
<<<
RATIONALE: 初見ユーザーがインポートなしに即座に描き始められること。user-order item7。
VERIFICATION: >>>
新規テンプレート上でパレットを開いたとき、マイルストーン用とタスク用の既定アイコンが選択可能な
状態で表示され、選んだアイコンを行へ配置できること。
<<<
RELATIONS:
- TYPE: Parent
  VALUE: STK-L0-006

[REQUIREMENT]
UID: ITEM-L1-003
TYPE: Functional
PRIORITY: Must
LAYER: L1_System
TITLE: 既定アイコン一覧の提示
STATEMENT: >>>
gr-scheduler は、選択可能な既定アイコンの一覧を、マイルストーン種別とタスク種別に分けて一覧
表示できること。
<<<
RATIONALE: どのアイコンが選べるかを一望させ、アフォーダンスを高める。user-order item8。
VERIFICATION: >>>
アイコン選択 UI を開いたとき、既定図形の全種がマイルストーン/タスクの区分とともに一覧され、
一覧から任意の図形を選択できること。
<<<
RELATIONS:
- TYPE: Parent
  VALUE: STK-L0-006

[REQUIREMENT]
UID: ITEM-L1-004
TYPE: Functional
PRIORITY: Must
LAYER: L1_System
TITLE: 既定図形セット (マイルストーン/タスク)
STATEMENT: >>>
gr-scheduler は、マイルストーン図形として circle 、triangle_up 、triangle_down 、square 、
star 、pentagon 、hexagon を提供し、タスク図形として line 、arrow 、double_arrow 、
segmented_bar 、chevron を提供すること。既定の star 図形は輪郭 (☆) として描画し、塗りは
ITEM-L1-006 / PROP-L1-002 の fill_color プロパティで与えること (既定描画が塗り潰しか輪郭かの
初期状態を輪郭へ変更するものであり、色指定の仕組み自体は変更しない)。加えて、パレットの
[...] 展開 UI から選択できる特殊マイルストーン図形として、file (右下が折れた紙 = 図面/資料
提出)、box3d (立体の箱 = ECU 等のハードウェア成果物)、floppy (フロッピー = SW リリース)、
cylinder (円筒 = サーバーへの SW デプロイ)、person (上半身の輪郭 = 偉い人への報告)、
smiley (笑顔 = 楽しいイベント)、beer (ビアタンブラー = 飲み会) の 7 種を既定図形セットに
追加すること。これら 7 種は milestoneShape を拡張する (taskShape は本要求の対象外・変更なし)。
マイルストーンアイコンの高さは、タスクバーの高さ比で +15% 大きく描画すること。
<<<
RATIONALE: >>>
user-order item9 の図形要求を機械可読な図形キーへ写像する。マイルストーンは
〇 △ ▽ □ ☆ 五角形 六角形、タスクは 直線 (ー) 、矢印 (→) 、双方向矢印 (⇔) 、区切りバー
(segmented_bar) 、矢羽根 (chevron) に対応する。star は塗り潰し星から輪郭 (☆) へ既定描画を
変更し、塗りは fill_color に委ねる (CR-004 Part 6b)。特殊マイルストーン 7 種
(file / box3d / floppy / cylinder / person / smiley / beer) は、アイコンインポート廃止
(CR-004 Part 6a) 後も、図面提出・SW リリース・デプロイ・報告・イベント等の意味を絵文字
(ITEM-L1-005) に頼らず既定図形として表現するため追加する (CR-004 Part 6c)。マイルストーンの
+15% 寸法は、点状のマイルストーンをタスクバーと釣り合う視認性に保つためである (CR-004 Part 2)。
milestoneShape enum への特殊 7 種の追加は実装フェーズでスキーマ
(docs/api/gr-scheduler.schema.json) に反映し、英語 enum キーは 40-data-format.sdoc の実装
フェーズ橋渡し節で暫定提示する (実装セッションで確定)。CR-004。
<<<
VERIFICATION: >>>
既定アイコン一覧に上記 7 種のマイルストーン図形と 5 種のタスク図形がすべて存在し、それぞれを
配置すると対応する形状で描画されること。既定の star が輪郭 (☆) で描画され、fill_color を与えると
当該色で塗られること。パレットの [...] から特殊マイルストーン 7 種
(file / box3d / floppy / cylinder / person / smiley / beer) が選択・配置でき、対応する形状で
描画されること。マイルストーンアイコンの高さが同一条件のタスクバー高さの +15% であること。
<<<
RELATIONS:
- TYPE: Parent
  VALUE: STK-L0-006

[REQUIREMENT]
UID: ITEM-L1-005
TYPE: Functional
PRIORITY: Should
LAYER: L1_System
TITLE: 絵文字アイコンの使用
STATEMENT: >>>
gr-scheduler は、アイテムのアイコンとして任意の絵文字を指定して表示できること。
<<<
RATIONALE: >>>
既定図形以外の直感的な表現手段。user-order item10。関連プロパティは PROP-L1-002 の
icon_emoji 項。
<<<
VERIFICATION: >>>
アイテムに絵文字を 1 文字指定したとき、その絵文字がアイコンとして行上に描画され、SVG 出力
および再読込後も同じ絵文字が保持されること。
<<<
RELATIONS:
- TYPE: Parent
  VALUE: STK-L0-006

[[/SECTION]]

[[SECTION]]
TITLE: 3. アイコンの色 (Icon Colors)

[REQUIREMENT]
UID: ITEM-L1-006
TYPE: Functional
PRIORITY: Must
LAYER: L1_System
TITLE: アイコンの枠色・塗り色の選択
STATEMENT: >>>
gr-scheduler は、アイテムのアイコンについて、枠色と塗り色をそれぞれ、パレットからの選択または
フルカラー指定のいずれかで設定できること。
<<<
RATIONALE: >>>
視認性と分類表現。パレットの 10 色定義および色弱者対応 (CUD) は 12-properties-i18n.sdoc の
PROP-L1-005 / PROP-L1-006 が主管する。本要求はアイテム側の設定操作を規定する。
user-order item11。
<<<
VERIFICATION: >>>
1 個のアイテムに対し、枠色をパレット色、塗り色をフルカラー指定に設定したとき、指定どおりの
枠色・塗り色でアイコンが描画され、設定値が保存されること。
<<<
RELATIONS:
- TYPE: Parent
  VALUE: STK-L0-006

[[/SECTION]]

[[SECTION]]
TITLE: 5. 略称の表示 (Abbreviation Label)

[REQUIREMENT]
UID: ITEM-L1-009
TYPE: Functional
PRIORITY: Must
LAYER: L1_System
TITLE: 略称のアイテム内部/付近への表示
STATEMENT: >>>
gr-scheduler は、アイテムの略称を、当該アイテムのアイコンの内部または付近に表示できること。
<<<
RATIONALE: >>>
一枚絵上で各アイテムを識別させる。略称の値は PROP-L1-002 の abbreviation 項。
user-order item22。
<<<
VERIFICATION: >>>
略称を設定したアイテムを配置したとき、略称文字列がアイコンの内部または近傍に表示され、
アイコンと視覚的に対応づけられること。
<<<
RELATIONS:
- TYPE: Parent
  VALUE: STK-L0-006

[REQUIREMENT]
UID: ITEM-L1-010
TYPE: Functional
PRIORITY: Should
LAYER: L1_System
TITLE: 略称表示位置のドラッグ移動
STATEMENT: >>>
gr-scheduler は、アイテムの略称の表示位置を、ユーザーのマウスドラッグによって当該アイテムを
基準とした相対位置へ移動できること。
<<<
RATIONALE: >>>
アイテムが狭所に込み合っても略称を見やすく保つ。座標とプロパティ (表示位置) の同期機構は
13-layout-alignment.sdoc が担うが、略称ラベルの移動操作自体はアイテム側の主管とする。
user-order item23。
<<<
VERIFICATION: >>>
略称ラベルをドラッグして移動したとき、略称が新しい相対位置に表示され、アイテム本体を移動しても
略称が同じ相対位置を保って追従すること。
<<<
RELATIONS:
- TYPE: Parent
  VALUE: STK-L0-006

[REQUIREMENT]
UID: ITEM-L2-002
TYPE: Functional
PRIORITY: Must
LAYER: L2_Component
TITLE: タスクラベルの既定表示位置 (バー内左揃え)
STATEMENT: >>>
タスクのラベル表示位置 labelPosition は、バー内左揃えを表す inner-left を既定値とし、タスクバーの
内側に左揃えで略称を描画すること。inner-left は、バー外の左を表す既存の left とは別概念として峻別
する (left = バー外・左、inner-left = バー内・左) 。
<<<
RATIONALE: >>>
パワポ日程表の慣習に合わせ、タスク略称をバー内に収めて一枚絵の密度を上げる。ITEM-L1-009 の「略称
のアイテム内部/付近への表示」を既定表示位置の観点から詳細化する。labelPosition の enum に inner-left
を追加する差分は次期スキーマ gr-scheduler.schema.next.json および 40-data-format.sdoc に反映する
(実装/スキーマ差分は実装フェーズ) 。CR-003 Part 2。
<<<
VERIFICATION: >>>
labelPosition を明示しないタスクを配置したとき略称がバー内・左揃えで描画され、left を明示したとき
はバー外・左に描画され、両者が視覚的に区別できること。
<<<
RELATIONS:
- TYPE: Parent
  VALUE: ITEM-L1-009

[REQUIREMENT]
UID: ITEM-L2-003
TYPE: Functional
PRIORITY: Must
LAYER: L2_Component
TITLE: マイルストーンラベルの表示位置 (アイコン右)
STATEMENT: >>>
マイルストーンのラベルは、マイルストーンアイコンの右 (icon-right) に描画すること。ラベル (略称)
のフォントサイズは、マイルストーンアイコンの寸法 (ITEM-L1-004 の +15% を反映した高さ) を基準に
算出すること。これはタスクがタスクバーの高さを基準にフォントサイズを決めるのと同様の考え方である。
<<<
RATIONALE: >>>
点状のマイルストーンアイコンは内部へ文字を収めにくいため、アイコンの右へ略称を置いて視認性を確保
する。ITEM-L1-009 の「略称のアイテム内部/付近への表示」をマイルストーンの配置観点から詳細化する。
ラベルフォントをマイルストーンアイコン寸法から導出するのは、+15% で拡大したアイコンと釣り合う
文字サイズを保つためである。CR-003 Part 2、CR-004 Part 2。
<<<
VERIFICATION: >>>
略称を設定したマイルストーンを配置したとき、略称がアイコンの右側に描画され、アイコンと視覚的に
対応づけられること。略称のフォントサイズがマイルストーンアイコンの寸法に比例して決まり、アイコンを
拡大するとフォントも比例して大きくなること。
<<<
RELATIONS:
- TYPE: Parent
  VALUE: ITEM-L1-009

[REQUIREMENT]
UID: ITEM-L2-004
TYPE: Functional
PRIORITY: Should
LAYER: L2_Component
TITLE: 担当者名の表示レイアウト (アイテム左・右詰め)
STATEMENT: >>>
担当者名 (PROP-L1-002 の assignee) を表示する場合、当該担当者名を対象タスク/マイルストーンの
左に、右詰めで配置すること。担当者名は、依存線の入口 (後続アイテムへ入る矢印 → ) の水平部分と
重ならないように配置すること。担当者名の表示/非表示を切り替えるトグル UI 自体は本要求の対象外で
あり、パレットの専用トグル (viewState.assigneeVisible) として PROP-L1-002 (CR-006 Part 7) で
規定する。本要求は表示するときのレイアウト規則のみを定める。
<<<
RATIONALE: >>>
担当者名をアイテム左・右詰めで揃えると、複数行に担当者名から各アイテムが並んだとき右端 (アイテム
側) が揃い一枚絵の可読性が上がる。依存線の左端入線 (DEP-L1-002 の middle_left アンカー、
DEP-L1-003 の左辺入規則) の水平部分と担当者名が干渉しないよう非干渉レイアウトとする。
ITEM-L1-009 の略称/周辺情報表示を担当者名の配置観点から詳細化する。CR-004 Part 5。
<<<
VERIFICATION: >>>
担当者名を表示したアイテムを配置したとき、担当者名がアイテムの左に右詰めで描画され、依存線が
左辺 (middle_left) から入るとき担当者名がその入口矢印の水平部分と重ならないことを描画計測で
確認すること。
<<<
RELATIONS:
- TYPE: Parent
  VALUE: ITEM-L1-009

[REQUIREMENT]
UID: ITEM-L2-005
TYPE: Non-Functional
PRIORITY: Must
LAYER: L2_Component
TITLE: アイテムのテキストは常にバーより前面に描く
STATEMENT: >>>
アイテムのテキスト (略称ラベル ITEM-L1-009、および担当者名 ITEM-L2-004) は、当該アイテムの
予定バーと実績バーの双方より常に前面へ描画すること。この前面関係は、予実の描画スタイル
(PLAN-L1-005 の Overlap / Separate) と可視フィルタ (PLAN-L1-002 の予定のみ/実績のみ/両方/
非表示) のどの組合せでも成り立つこと。すなわち、後から生成された実績バーが略称や担当者名を
覆い隠してはならない。

本前面関係は、描画順に依存する偶然ではなく構造的な不変条件として保つこと。テキストは専用の
テキスト層 (最前面に置かれ、表示切替や再描画で取り除かれない層) に属し、バー・マーカーの類は
その層より背面へ挿入すること。したがって、バーやマーカーが遅延生成・削除・再生成されても、
またスタイル/可視フィルタを何度切り替えても、前面関係が崩れないこと。
<<<
RATIONALE: >>>
Overlap では濃色の実績バーが淡色の予定バーへ重なり、Separate では実績バーが新たに生成される。
これらのバーがテキストより後から DOM へ追加されると、SVG の描画順 (後の兄弟が前面) により
略称が実績バーの下へ隠れ、一枚絵上でアイテムを識別できなくなる。実際にこの事象が発生したため
(DEF-009)、描画順の偶然に頼らず、テキストを常に最後に描かれる専用層へ隔離することで不変条件と
して固定する。ITEM-L1-009 の略称表示・ITEM-L2-004 の担当者名表示を重なり順の観点から詳細化する。
DEF-009。
<<<
VERIFICATION: >>>
実績を持つタスクに略称と担当者名を表示し、planActualStyle を overlap / separate、
planActualDisplay を予定のみ/実績のみ/両方の各組合せで切り替えたとき、略称と担当者名がいずれの
組合せでも実績バー・予定バーより前面に描かれることを確認すること。実績バーの生成・削除を伴う
表示切替を往復させた後、およびアイテムの図形が差し替えられた後でも、テキスト層が最前面のまま
維持されることを確認すること。
<<<
RELATIONS:
- TYPE: Parent
  VALUE: ITEM-L1-009

[[/SECTION]]

[[SECTION]]
TITLE: 6. 期限マーカー (Deadline / Target Date)

[REQUIREMENT]
UID: ITEM-L1-011
TYPE: Functional
PRIORITY: Should
LAYER: L1_System
TITLE: 期限 (目標終了日) マーカーの表示
STATEMENT: >>>
gr-scheduler は、アイテムに任意の期限 (目標終了日) item.targetDate を持たせ、バー端 (startDate /
endDate) とは独立した「ここまで」の目標マーカーとして当該日付位置に描画できること。
targetDate は MSPDI の Deadline と往復すること。マーカーの具体的な形状・配置は実装時に確定
する。
<<<
RATIONALE: >>>
俯瞰日程表では、計画バーの端とは別に「守るべき期限」を一目で示したい需要がある。MS Project の
Deadline は制約 (Constraint) と異なりスケジューラを動かさない目標線であり、スケジューラを持た
ない gr-scheduler と相性が良い。CR-001 (承認 2026-07-19) Part C で採用する。予実の front 規則
(PLAN-L2-001) や表示スタイル (PLAN-L1-005) とは独立の属性であり、データ形式は
`40-data-format.sdoc` DATA-JSON-015 / DATA-MSPDI-009 を参照する。
<<<
VERIFICATION: >>>
targetDate を設定したアイテムで、当該日付位置に期限マーカーがバー端と独立して描画され、保存・
再読込後も保持されること。MSPDI へ Export すると Deadline に、Import で targetDate に往復する
ことを確認すること。
<<<
RELATIONS:
- TYPE: Parent
  VALUE: STK-L0-011

[[/SECTION]]

[[SECTION]]
TITLE: 7. 選択 (Selection)

[REQUIREMENT]
UID: SEL-L1-001
TYPE: Functional
PRIORITY: Must
LAYER: L1_System
TITLE: 矩形選択による複数選択
STATEMENT: >>>
gr-scheduler は、キャンバスの空き領域 (どのアイテム/コメント上でもない位置) からのドラッグで
矩形選択を開始し、矩形に交差する複数のアイテム (およびコメント) をまとめて選択できること。
矩形選択は選択集合を形成する操作であり、ITEM-L1-001 が規定する「各アイテムが独立に選択できる」
ことと整合する (各アイテムの独立選択性を保ったまま複数を 1 つの選択集合へ束ねる)。
<<<
RATIONALE: >>>
マルチバー一枚絵の上で複数アイテムを一括して移動・複製・削除するための前提となる操作。現行仕様は
ITEM-L1-001 の独立選択に留まり、矩形選択自体を明文化した要求が無かったため本 CR で新設する。
PowerPoint 的な選択操作系 (矩形選択 + 増減) の基点を成す。CR-007。
<<<
VERIFICATION: >>>
空き領域からドラッグして矩形を描いたとき、矩形に交差する複数のアイテム (およびコメント) が
一括で選択状態となり、各要素が個別にも選択可能なまま保たれること。
<<<
RELATIONS:
- TYPE: Parent
  VALUE: STK-L0-001

[REQUIREMENT]
UID: SEL-L1-002
TYPE: Functional
PRIORITY: Must
LAYER: L1_System
TITLE: Ctrl+クリックによる選択の増減
STATEMENT: >>>
gr-scheduler は、 ``Ctrl+click`` により、クリックしたアイテムの選択集合への所属をトグルできる
こと (未選択なら選択集合へ追加し、選択済みなら選択集合から除外する)。矩形選択 (SEL-L1-001) の
結果集合に対しても ``Ctrl+click`` で個別に追加・除外でき、矩形選択で選び過ぎた/選び足りなかった
分を続けて補正できること (PowerPoint 式の増減)。
<<<
RATIONALE: >>>
矩形選択だけでは過不足の補正ができない。 ``Ctrl+click`` の増減により、選択集合を対話的に
整えられるようにする。選択集合の共通編集基盤 (STK-L0-008 の編集効率化) の一部として規定する。
CR-007。
<<<
VERIFICATION: >>>
未選択アイテムを ``Ctrl+click`` すると選択集合へ加わり、選択済みアイテムを ``Ctrl+click`` すると
選択集合から外れること。矩形選択後に ``Ctrl+click`` で個別の追加・除外ができることを確認すること。
<<<
RELATIONS:
- TYPE: Parent
  VALUE: STK-L0-008

[REQUIREMENT]
UID: SEL-L2-001
TYPE: Functional
PRIORITY: Must
LAYER: L2_Component
TITLE: ポインタ操作の当たり判定優先順位 (増減・矩形選択・移動の峻別)
STATEMENT: >>>
選択コントローラは、ポインタ操作の起点と修飾キーに応じて、次の優先順位で挙動を確定すること。

.. list-table::
   :header-rows: 1
   :widths: 40 60

   * - 起点/修飾
     - 挙動
   * - ``Ctrl+click`` (アイテム上)
     - クリックしたアイテムの選択集合への所属をトグルするのみ。ドラッグ/移動は開始しない。
   * - 空き領域からのドラッグ
     - 矩形選択 (SEL-L1-001) を開始する。
   * - 選択済みアイテム上での修飾なしドラッグ
     - 選択集合の移動 (ALIGN-L1-004) を開始する。

これにより ``Ctrl+click`` による選択増減が誤ってドラッグ移動を起動しないこと、矩形選択と選択集合
移動の起点が競合しないことを保証する。
<<<
RATIONALE: >>>
``Ctrl+click`` の増減 (SEL-L1-002) とアイテム上でのドラッグ移動 (ALIGN-L1-004) が同じアイテム上で
起こり得るため、当たり判定の優先順位を明示して衝突を防ぐ。CR-007 §7 の当たり判定優先順位 (D-6) の
決定事項を反映する。CR-007。
<<<
VERIFICATION: >>>
アイテム上での ``Ctrl+click`` が選択のトグルのみを行い移動を起動しないこと、空き領域からのドラッグ
が矩形選択を、選択済みアイテム上の修飾なしドラッグが選択集合移動を、それぞれ起動することを確認する
こと。
<<<
RELATIONS:
- TYPE: Parent
  VALUE: SEL-L1-002

[[/SECTION]]
