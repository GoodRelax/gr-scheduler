[DOCUMENT]
TITLE: gr-scheduler 要求仕様 - 整列とレイアウト・双方向同期 (L1-L3)

[GRAMMAR]
IMPORT_FROM_FILE: gr-scheduler-grammar.sgra

[TEXT]
STATEMENT: >>>
本書は gr-scheduler のアイテム整列 (上下左右揃え) 、WYSIWYG なドラッグ編集、およびアイテム
移動と日付プロパティの双方向同期に関するシステム要求 (L1) を定義し、整列制約ソルバと座標-日付
写像をコンポーネント要求 (L2) へ詳細化する。各 L1 要求は Parent 関係でステークホルダ要求
STK-L0-003 (整列と揃え) および STK-L0-005 (パワポ感覚の WYSIWYG 編集) をトレースする。
出典は user-order.md item3, item5, item12 (★アイコン移動連動プロパティ自動更新)。
略称ラベル位置のドラッグ移動操作は 11-items-icons.sdoc (ITEM-L1-010) が主管する (重複回避)。
<<<

[[SECTION]]
TITLE: 1. 整列と揃え (Alignment)

[REQUIREMENT]
UID: ALIGN-L1-001
TYPE: Functional
PRIORITY: Must
LAYER: L1_System
TITLE: アイテムの上下左右揃え
STATEMENT: >>>
gr-scheduler は、複数のマイルストーン/タスクとそのアイコンを上下左右に揃えられ、同じタイミング
で始まるタスクや同種のマイルストーンを同じ高さに表示できること。
<<<
RATIONALE: 一枚絵の可読性の要。整列が崩れると俯瞰性が損なわれる。user-order item3。
VERIFICATION: >>>
同一開始日の複数タスクを上揃えの対象に指定したとき、それらのアイコン上端が同一の垂直座標に
揃い、同種マイルストーンを高さ揃えの対象に指定したとき同一の高さに整列すること。
<<<
RELATIONS:
- TYPE: Parent
  VALUE: STK-L0-003

[REQUIREMENT]
UID: ALIGN-L2-001
TYPE: Functional
PRIORITY: Must
LAYER: L2_Component
TITLE: 整列制約ソルバ (共有ベースラインへのスナップ)
STATEMENT: >>>
アイテム移動が確定したとき、整列制約ソルバは、対象アイテムに近接する既存の共有ベースライン
(同一開始日の垂直線・同種アイテムの水平高さ) を検出し、しきい値内にあるアイテムを当該ベース
ラインへスナップして整列を維持すること。
<<<
RATIONALE: >>>
上下左右揃え (ALIGN-L1-001) を内部アルゴリズムとして詳細化する。ドラッグのたびに共有ベース
ラインへ吸着させることで、手作業の微調整なしに整列を保つ。
<<<
VERIFICATION: >>>
既存の共有ベースラインからしきい値内にアイテムをドラッグして離したとき、当該アイテムがベース
ラインへスナップし、しきい値外へ離したときはスナップせず自由位置に留まること。
<<<
RELATIONS:
- TYPE: Parent
  VALUE: ALIGN-L1-001

[REQUIREMENT]
UID: ALIGN-L2-003
TYPE: Functional
PRIORITY: Must
LAYER: L2_Component
TITLE: ラベルはみ出し時の同一セクション内衝突回避 (縦オフセット)
STATEMENT: >>>
タスクラベルの表示がタスクバー幅を超えてはみ出すことは許容する。ただし、あるタスクのラベルの
はみ出しが同一セクション内の他タスクの表示と視覚的に重なる場合、マルチバー・レイアウトエンジンは、
当該タスクを同一セクション内で高さ (縦オフセット) を変えて配置し、重なりを回避すること。回避後も
ALIGN-L1-001 の上下左右揃えの意図を可能な範囲で維持すること。
<<<
RATIONALE: >>>
ラベルは情報量確保のためはみ出しを許すが、はみ出しによる可読性低下 (重なり) は避ける。ALIGN-L2-001
の整列制約ソルバの枠組みに、ラベルのはみ出しによる衝突を追加の制約として組み込み、同一セクション内
でのマルチバー衝突回避 (縦方向の段組み) として解決する。CR-003 Part 2。
<<<
VERIFICATION: >>>
同一セクションに、ラベルがはみ出して隣接タスクと重なる配置を作ったとき、当該タスクの高さ (縦位置)
が同一セクション内で変わって重なりが解消され、はみ出し自体は許容 (ラベルを切り詰めない) される
こと。
<<<
RELATIONS:
- TYPE: Parent
  VALUE: ALIGN-L1-001

[REQUIREMENT]
UID: ALIGN-L2-004
TYPE: Functional
PRIORITY: Must
LAYER: L2_Component
TITLE: サブレーン割当順の下から上への反転 (最上段=マイルストーン)
STATEMENT: >>>
マルチバー・レイアウトエンジンは、同一行/セクション内で時間的に重なるアイテムのサブレーン (段) の
割当順を、上から下ではなく下から上の順で行うこと。すなわち最上段のサブレーンにマイルストーンが
置かれ、下側のタスク群から上のマイルストーンへ依存線が立ち上る構図となること。本規則はタスクバーと
マイルストーンの両方に適用する。積み順を反転した後も、ALIGN-L1-001 の上下左右揃えと ALIGN-L2-003 の
ラベルはみ出し縦オフセット衝突回避の意図は維持し、反転させるのは割当順序の起点のみとすること。
<<<
RATIONALE: >>>
最上段をマイルストーンとする構図は、IM8 で実装済みの依存線の上下端入線 (DEP-L1-003 の後続上端/下端
からの侵入、DEP-L2-001) と組み合わせたとき、下のタスク群から上のマイルストーンへ依存線が視覚的に
立ち上る一枚絵を作り可読性を高める。本規則はレイアウトエンジン ARCH-C-011 が実装する ITEM-L1-001 の
重なり回避と ALIGN-L1-001 の上下揃えの割当起点を反転させるものである。対象がタスクバーと
マイルストーンの両方であることはユーザー確認済み (2026-07-21)。CR-004 Part 1。
<<<
VERIFICATION: >>>
同一行/セクションに時間的に重なるタスクとマイルストーンを配置したとき、サブレーンの割当が下から上の
順で行われ最上段にマイルストーンが置かれること、反転後も上下左右揃えとラベルはみ出し衝突回避が
機能することを単体テストおよび描画計測で確認すること。
<<<
RELATIONS:
- TYPE: Parent
  VALUE: ALIGN-L1-001

[REQUIREMENT]
UID: ALIGN-L2-005
TYPE: Constraint
PRIORITY: Must
LAYER: L2_Component
TITLE: フォント大設定時のセクション行マージン確保
STATEMENT: >>>
フォントスケールが大きく設定されたとき、マルチバー・レイアウトエンジンは、左ペインのセクション
ツリー (大分類/中分類/小分類の各行) の行高マージンをフォントサイズに連動して増やし、小分類の
一番上の行が中分類の行と重ならないようにすること。
<<<
RATIONALE: >>>
フォントスケールはセクション表示等へ適用され (CR-005 で確定した対象要素)、大フォント設定時に階層行が
重なると可読性が損なわれる。行高マージンをフォントサイズに連動させて確保する。本規則はレイアウト
エンジン ARCH-C-011 が算出する行・セクションの縦配置に対する制約である。CR-004 Part 3。
<<<
VERIFICATION: >>>
フォントを大サイズに設定した状態で左ペインのセクションツリーを表示したとき、小分類の一番上の行が
中分類の行と重ならないことを描画計測で確認すること。
<<<
RELATIONS:
- TYPE: Parent
  VALUE: ALIGN-L1-001

[[/SECTION]]

[[SECTION]]
TITLE: 2. WYSIWYG 編集 (Direct Manipulation)

[REQUIREMENT]
UID: ALIGN-L1-002
TYPE: Functional
PRIORITY: Must
LAYER: L1_System
TITLE: ドラッグによる作成・移動・リサイズ
STATEMENT: >>>
gr-scheduler は、マイルストーン/タスクを、マウスドラッグによって作成し、キャンバス上で移動し、
タスクの期間を端のドラッグでリサイズでき、操作結果を見たまま (WYSIWYG) に反映すること。
<<<
RATIONALE: パワポ/Excel の代替として直感操作が定着の前提。user-order item5。
VERIFICATION: >>>
パレットから図形を選びキャンバスへドラッグして作成でき、配置後のアイテムをドラッグで移動でき、
タスクの端をドラッグすると期間の長さが変わり、いずれも操作中に結果が即時に描画されること。
<<<
RELATIONS:
- TYPE: Parent
  VALUE: STK-L0-005

[[/SECTION]]

[[SECTION]]
TITLE: 3. 双方向同期 (Coordinate-Date Bidirectional Sync)

[REQUIREMENT]
UID: ALIGN-L1-003
TYPE: Functional
PRIORITY: Must
LAYER: L1_System
TITLE: 移動連動のプロパティ自動更新 (双方向同期)
STATEMENT: >>>
アイテムがドラッグで移動またはリサイズされたとき、gr-scheduler は、当該アイテムの開始日・
終了日・表示位置プロパティを、新しいキャンバス座標に対応する値へ自動で更新すること。また、
これらのプロパティが編集されたとき、アイテムの表示位置を対応する座標へ自動で更新すること。
<<<
RATIONALE: >>>
★追加要望。座標とプロパティを常に一致させ、見た目とデータの二重管理をなくす。user-order
item12 (アイコン移動連動でプロパティ自動更新)、STK-L0-005 の双方向同期。
<<<
VERIFICATION: >>>
タスクをドラッグで右へ移動すると start_date/end_date が移動量に対応して更新され、逆に
start_date をプロパティ編集で変更するとアイテムが対応する座標へ移動し、双方向で値と表示が
一致すること。
<<<
RELATIONS:
- TYPE: Parent
  VALUE: STK-L0-005

[REQUIREMENT]
UID: ALIGN-L2-002
TYPE: Functional
PRIORITY: Must
LAYER: L2_Component
TITLE: 座標-日付の双方向写像
STATEMENT: >>>
座標-日付マッパは、現在の横軸スケール (時間軸の原点日付と 1 日あたりのピクセル幅) に基づき、
キャンバスの x 座標を日付へ変換する関数と、日付を x 座標へ変換する関数を、互いに逆写像となる
ように提供し、往復変換で丸め誤差により日付がずれないこと。
<<<
RATIONALE: >>>
双方向同期 (ALIGN-L1-003) の中核アルゴリズムを詳細化する。座標->日付と日付->座標を単一の
スケール定義から導出し、整合を保証する。ズームによりスケールが変わっても同じ定義を用いる。
<<<
VERIFICATION: >>>
任意の日付を x 座標へ変換し、その x 座標を日付へ逆変換したとき元の日付に一致し (日単位で
一致) 、ズーム率を変えても往復整合が保たれること。
<<<
RELATIONS:
- TYPE: Parent
  VALUE: ALIGN-L1-003

[[/SECTION]]

[[SECTION]]
TITLE: 4. 複数選択アイテムの移動 (Multi-Item Move)

[REQUIREMENT]
UID: ALIGN-L1-004
TYPE: Functional
PRIORITY: Must
LAYER: L1_System
TITLE: 複数選択アイテムの移動 (左右一括日付シフト / 上下分類再割当)
STATEMENT: >>>
gr-scheduler は、複数選択したアイテム (SEL-L1-001 / SEL-L1-002 で形成した選択集合) をドラッグで
移動するとき、ドラッグ方向に応じて次の 2 モードで移動すること。

- 左右移動 = 一括日付シフト: 選択した全アイテムの開始日・終了日を同一移動量だけシフトする
  (まとめて遅延/前倒し)。ALIGN-L1-002 のドラッグ移動および ALIGN-L1-003 の移動連動プロパティ
  自動更新を、複数選択への拡張として適用する。
- 上下移動 = 分類再割当: 選択集合が共有する最深の分類レベル (大分類/中分類/小分類) における隣接
  sibling へ、所属分類のみを付け替える。付替えの詳細規則は ALIGN-L2-006 が定める。

本要求は選択集合の移動を規定するものであり、ALIGN-L2-003 のラベルはみ出し縦オフセット衝突回避とは
干渉しない (再割当・シフト後のレイアウトに対して ALIGN-L2-003 が独立に働く)。
<<<
RATIONALE: >>>
複数アイテムの一括操作を、左右は日付の一括シフト、上下は所属分類の付替えという 2 つの直感的な
意味へ写像する。上下移動を階層構造の組替えではなく所属分類の変更のみで完結させることで、アイテムの
複製や新規行生成を伴わずロジックを単純に保つ。CR-007 Part 2 (ユーザー協議確定・★2)。
<<<
VERIFICATION: >>>
複数選択したアイテムを左右へドラッグすると全アイテムの開始日・終了日が同一移動量だけシフトすること、
上下へドラッグすると最深共有分類レベルの隣接 sibling へ再割当され上位レベルの分類が変化しないこと、
いずれの移動後も ALIGN-L2-003 のラベル衝突回避が独立に機能することを確認すること。
<<<
RELATIONS:
- TYPE: Parent
  VALUE: STK-L0-005

[REQUIREMENT]
UID: ALIGN-L2-006
TYPE: Functional
PRIORITY: Must
LAYER: L2_Component
TITLE: 上下移動の分類再割当アルゴリズム (最深共有レベル判定・隣接 sibling・端停止)
STATEMENT: >>>
整列制約ソルバは、複数選択アイテムの上下移動 (ALIGN-L1-004 の分類再割当モード) を次の規則で
解決すること。

- 選択アイテムが大分類のみ共有 → 隣接するセクション (major) へ再割当する。
- 中分類まで共有 → 同一 major 内の隣接する中分類 (middle) へ再割当する。
- 小分類まで共有 → 同一 middle 内の隣接する小分類 (minor) へ再割当する。
- 上位レベルの分類は維持し、再割当対象レベル (最深共有レベル) のみを変更する。
- 分類ツリーの端 (隣接 sibling が存在しない最初/最後の sibling) では移動を発生させず、
  無操作 (silent no-op) とする。禁止カーソル表示等の UX フィードバックは本スコープの対象外とする。

再割当は所属分類 (majorCategory / middleCategory / minorCategory と対応する rowId、および
sections[].rowIds[]) の変更のみで完結し、大中小の親子関係 (階層構造そのもの) およびアイテム ID は
不変とする。最深共有レベルの判定は SECT-L2-001 のインデント階層 (大中小のツリー構造) に基づく。
<<<
RATIONALE: >>>
上下移動を「所属分類の付替え」に閉じることで、アイテムの複製や行生成を伴わずに再配置できる。
最深共有レベルのみを対象とし上位を固定することで、選択集合の分類的まとまりを保ったまま隣へ動かせる。
分類ツリー端での無操作 (silent no-op) は CR-007 §7 の決定事項 (D-5) を反映する。CR-007 Part 2。
<<<
VERIFICATION: >>>
大分類のみ共有する選択集合が隣接セクションへ、中分類まで共有する集合が隣接中分類へ、小分類まで
共有する集合が隣接小分類へ再割当され、上位レベルが不変であること。分類ツリーの端で上下移動しても
何も起きない (silent no-op) こと。再割当後もアイテム ID と階層構造が不変であることを確認すること。
<<<
RELATIONS:
- TYPE: Parent
  VALUE: ALIGN-L1-004

[[/SECTION]]
