[DOCUMENT]
TITLE: gr-scheduler 要求仕様 - 分類とセクション (L1-L3)

[GRAMMAR]
IMPORT_FROM_FILE: gr-scheduler-grammar.sgra

[TEXT]
STATEMENT: >>>
本書は gr-scheduler の分類 (水平線) とセクション管理に関するシステム要求 (L1) と、その詳細化
(L2) を定義する。分類する水平線、複数行を束ねる ★ セクション化と順序入替、 ★ セクションの
表示/非表示、 ★ 非表示セクションを水平線左端の小タブから再表示する仕組み、分類名の左ペイン表示を
扱う。各要求は Parent 関係で L0 (STK-L0-009) を詳細化する。左固定ペインの存在とスクロール連動は
10-canvas-view が担当する。
<<<

[[SECTION]]
TITLE: 1. 分類の水平線 (Classification Lines)

[REQUIREMENT]
UID: SECT-L1-001
TYPE: Functional
PRIORITY: Must
LAYER: L1_System
TITLE: 分類する水平線
STATEMENT: >>>
本システムは、キャンバス上に、マイルストーン/タスクを分類する水平線を任意の位置へ引けること。
<<<
RATIONALE: 行群を区切って整理する基本手段。user-order item35。
RELATIONS:
- TYPE: Parent
  VALUE: STK-L0-009

[REQUIREMENT]
UID: SECT-L1-006
TYPE: Functional
PRIORITY: Must
LAYER: L1_System
I18N: Yes
TITLE: 分類名の左ペイン表示
STATEMENT: >>>
本システムは、各分類およびセクションの名称を、画面左側の分類ペインに表示すること。分類名
(大分類・中分類・小分類の 3 階層すべて) のフォントサイズは、フォントスケール ``[S][M][L]``
(TOOL-L1-002) に追従すること。このうち最下位の小分類の分類名フォントサイズは、アイテムの
コメント本文フォント (CURS-L2-002) が一致させる基準値とすること。
<<<
RATIONALE: >>>
どの帯が何の分類かを常時提示する。分類名は多言語文字列のため i18n 対象。分類ペインの存在と
その幅可変・スクロール連動は 10-canvas-view が担当する。user-order item40。分類名フォントの
``[S][M][L]`` 追従と、小分類名をコメント本文フォント (CURS-L2-002) の基準値とする規定は CR-005。
<<<
RELATIONS:
- TYPE: Parent
  VALUE: STK-L0-009

[TEXT]
STATEMENT: >>>
**設計メモ (mock feedback):** 分類ペインの幅はユーザーがドラッグで可変にできる (実機モックの
フィードバック。要求は 10-canvas-view の CANVAS-L2-001)。大分類・中分類・小分類の階層は
インデント (字下げ) で表現し、階層ごとに独立したカラムを設けない (SECT-L2-001)。これにより
狭い分類ペインでも階層と情報密度を両立する。
<<<

[REQUIREMENT]
UID: SECT-L2-001
TYPE: Functional
PRIORITY: Should
LAYER: L2_Component
TITLE: 階層のインデント表現
STATEMENT: >>>
分類ペインは、大分類・中分類・小分類の階層をインデント (字下げ) で表現し、階層ごとに独立した
カラムを設けないこと。各階層の分類名フォントサイズはフォントスケール ``[S][M][L]`` (TOOL-L1-002)
に追従し、最下位の小分類の分類名フォントサイズはアイテムのコメント本文フォント (CURS-L2-002) の
基準値とすること。
<<<
RATIONALE: >>>
カラム分割は左ペインを横に広げ描画領域を圧迫する。インデント表現で狭い幅でも階層を示す。
SECT-L1-006 の内部表現規則。user-order item40 (mock feedback)。小分類名フォントをコメント本文
フォントの基準値とする点と ``[S][M][L]`` 追従は CR-005。
<<<
RELATIONS:
- TYPE: Parent
  VALUE: SECT-L1-006

[[/SECTION]]

[[SECTION]]
TITLE: 2. セクション化と順序 (Sectioning & Order)

[REQUIREMENT]
UID: SECT-L1-002
TYPE: Functional
PRIORITY: Must
LAYER: L1_System
TITLE: 複数行のセクション化と順序入替
STATEMENT: >>>
本システムは、複数の分類行を束ねて 1 つのセクションとし、セクション単位で表示順序を入れ替え
られること。
<<<
RATIONALE: 大規模日程を意味のまとまりで整理し、並び順を柔軟に変える。 ★ user-order item36。
RELATIONS:
- TYPE: Parent
  VALUE: STK-L0-009

[REQUIREMENT]
UID: SECT-L1-003
TYPE: Functional
PRIORITY: Must
LAYER: L1_System
TITLE: セクションの表示/非表示切替
STATEMENT: >>>
本システムは、各セクションの表示/非表示を個別に切り替えられること。
<<<
RATIONALE: 注目したいセクションだけを残して俯瞰性を高める。 ★ user-order item37。
RELATIONS:
- TYPE: Parent
  VALUE: STK-L0-009

[[/SECTION]]

[[SECTION]]
TITLE: 3. 非表示セクションの再表示 (Reveal via Tabs)

[REQUIREMENT]
UID: SECT-L1-004
TYPE: Functional
PRIORITY: Must
LAYER: L1_System
TITLE: 小タブによる非表示セクションの再表示
STATEMENT: >>>
セクションを非表示にしたとき、本システムは、水平線の左端に再表示用の小タブを表示し、その小タブへ
の操作で当該セクションを再表示すること。
<<<
RATIONALE: 隠したセクションの存在と復帰手段を、場所を取らずに提示する。 ★ user-order item38。
VERIFICATION: >>>
セクションを非表示にすると水平線左端に小タブが 1 つ現れ、その小タブを操作すると当該セクションが
元の順序位置へ再表示されることを確認する。
<<<
RELATIONS:
- TYPE: Parent
  VALUE: STK-L0-009

[REQUIREMENT]
UID: SECT-L1-005
TYPE: Constraint
PRIORITY: Must
LAYER: L1_System
TITLE: 小タブ増加による対応と水平線の非肥大
STATEMENT: >>>
非表示セクションが増えた場合、本システムは、水平線左端の小タブ数を増やすことで対応し、水平線
自体の幅 (太さ) は増やさないこと。
<<<
RATIONALE: >>>
非表示が増えても水平線を太らせて描画領域を圧迫しない。小タブの個数で表現を拡張する。
★ user-order item39。
<<<
VERIFICATION: >>>
非表示セクションを複数にしたとき、水平線の太さが一定のまま、小タブの個数だけが非表示数に応じて
増えることを確認する。
<<<
RELATIONS:
- TYPE: Parent
  VALUE: STK-L0-009

[[/SECTION]]

[[SECTION]]
TITLE: 4. 分類のコピー&ペースト (Classification Copy-Paste)

[REQUIREMENT]
UID: SECT-L1-007
TYPE: Functional
PRIORITY: Must
LAYER: L1_System
TITLE: 分類の複製 (直下挿入・名前 suffix・配下の新 ID 複製)
STATEMENT: >>>
本システムは、大分類または中分類を選択した状態で、左ペインの分類ノードの並替 (▲▼) 近傍に
配置したコピペアイコン (2 枚重ねの書類) の操作により、当該分類を複製できること。複製の規則は
次のとおりとする。

- 複製位置: 選択中の分類の直下 (次の同レベル分類の直前) に複製を挿入する。大分類選択時は当該
  大分類の直下、中分類選択時は当該中分類の直下へ挿入する。
- 複製名: 既存名 + 次の空き番号 suffix とする (例: ``Body`` → ``Body-1`` 。 ``Body-1`` が既存
  ならば ``Body-2`` )。
- 複製の中身: 配下の行 (rows) とアイテム (items) を新規 ID で複製し、所属分類
  (majorCategory / middleCategory / minorCategory) と rowId、および sections[].rowIds[] を複製側へ
  張り替える。

複製 UI の操作子 (コピペアイコン) の配置は、SECT-L2-001 のインデント階層で表現する分類ノードの
並替 (▲▼) 近傍とし、既存のアイテムのコピー&ペースト (TOOL-L1-003) の考え方を分類複製へ準用する。
<<<
RATIONALE: >>>
類似構成の分類 (例: 車種違いで同じフェーズ構成) を一から作り直す負荷を下げる。複製位置・名前
suffix・配下の新 ID 複製という規則は CR-007 §7 の決定事項 (★1) を反映する。操作子を左ペイン
▲▼ 近傍のコピペアイコンとすることでセクション並替 (SECT-L1-002) の操作系と一貫させる。CR-007
Part 5 (ユーザー協議確定・★1)。
<<<
VERIFICATION: >>>
大分類/中分類を選択してコピペアイコンを操作すると、選択中の分類の直下に複製が挿入され、複製名が
既存名 + 次の空き番号 suffix ( ``xxx-1`` 、既存なら ``xxx-2`` ) で採番されること。配下の行・
アイテムが新規 ID で複製され、rowId と所属分類が複製側へ正しく張り替わることを確認すること。
<<<
RELATIONS:
- TYPE: Parent
  VALUE: STK-L0-009

[REQUIREMENT]
UID: SECT-L2-002
TYPE: Functional
PRIORITY: Must
LAYER: L2_Component
TITLE: 分類複製時の ID 再割当と依存線の扱い
STATEMENT: >>>
分類複製 (SECT-L1-007) の実行時、複製処理は依存線 (DEP-L1-001) を次の規則で扱うこと。

- 複製対象サブツリーの内部で閉じる依存線 (始点・終点の両端が複製対象サブツリー内にあるもの) は、
  複製側でも新規 ID へ張り替えて再現する。
- 複製境界をまたぐ依存線 (一端が複製対象サブツリーの外にあるもの) は、複製側では生成しない
  (原本アイテムを指したまま残さない)。

複製された行・アイテム・依存線はすべて新規 ID を持ち、原本 (複製元) には一切影響しないこと。
本規則は DATA-JSON-003 / DATA-JSON-004 / DATA-JSON-005 の新規 ID 生成および rowId/分類の張替えの
対象となる。
<<<
RATIONALE: >>>
複製境界をまたぐ依存線を複製側に残すと、複製が原本アイテムを指す不整合が生じるため落とす。一方、
複製サブツリー内で閉じる依存線は複製側でも意味を保つため新規 ID で再現する。この内部依存の再現と
境界またぎ依存の破棄の区別は CR-007 §7 の決定事項 (D-4) を反映する。CR-007 Part 5。
<<<
VERIFICATION: >>>
複製対象サブツリー内で閉じる依存線が複製側で新規 ID へ張り替えて再現されること、複製境界をまたぐ
依存線が複製側では生成されず原本アイテムを指したまま残らないこと、複製された行・アイテム・依存線が
すべて新規 ID を持ち原本に影響しないことを確認すること。
<<<
RELATIONS:
- TYPE: Parent
  VALUE: SECT-L1-007

[[/SECTION]]
