[DOCUMENT]
TITLE: gr-scheduler 要求仕様 - ツール操作と透かし (L1-L3)

[GRAMMAR]
IMPORT_FROM_FILE: gr-scheduler-grammar.sgra

[TEXT]
STATEMENT: >>>
本書は gr-scheduler の **ツール操作と透かし** ドメインのシステム要求 (L1) 以下を定義する。
対象は、フローティングパレット (item6.2)、全体フォントサイズ切替 (item6.3)、アイテムの
コピー&ペースト (item13)、Undo/Redo とショートカットキー (item53)、パレット非選択時の
透明化 (item58)、日程表の透かし (item59, item59.1-59.3) である。各 L1 要求は
ステークホルダ要求 (STK-L0-008 / STK-L0-013 / STK-L0-019 / STK-L0-021 / STK-L0-022) へ
Parent 関係でトレースする。
<<<

[[SECTION]]
TITLE: 1. パレットとフォント (Palette & Font)

[REQUIREMENT]
UID: TOOL-L1-001
TYPE: Non-Functional
PRIORITY: Should
LAYER: L1_System
TITLE: ツールパレットのフローティング表示
STATEMENT: >>>
本システムは、ツール操作用パレットを画面端の固定バーとしてではなくフローティング要素として
表示し、ユーザーがパレットをキャンバス上の任意位置へ移動できること。
<<<
RATIONALE: 固定バーによる描画面積の圧迫を避け、狭い画面に最大の情報量を収める。user-order item6.2 (★★)。
VERIFICATION: パレットがキャンバスに重ねて表示され、ドラッグで位置を変更でき、固定バー領域を占有しないこと。
RELATIONS:
- TYPE: Parent
  VALUE: STK-L0-021

[REQUIREMENT]
UID: TOOL-L2-006
TYPE: Constraint
PRIORITY: Should
LAYER: L2_Component
TITLE: ヘッダー P とパレット最小化ボタンの双方向状態同期
STATEMENT: >>>
フローティングパレットコンポーネントは、パレット自身の最小化ボタン (パレット内の ``[-]`` 相当) と
ヘッダーのパレット表示/最小化トグル ``[P]`` (TOOL-L1-008 の第 4 要素) の状態を双方向に同期する
こと。すなわち、いずれか一方の操作で最小化/復帰したとき他方の表示状態 ( ``aria-expanded`` 等) が
追従し、両者が常に同一の最小化状態を指すこと。最小化中はヘッダー ``[P]`` を不活性 (色変化) 表示と
し、パレットが最小化されていることをユーザーが見失わないようにすること。
<<<
RATIONALE: >>>
パレット最小化時にパレットの居所を見失う (迷子になる) 問題への対策として、ヘッダー ``[P]`` と
パレット側最小化ボタンを双方向連動させ、どちらから操作しても状態が一致するようにする。
TOOL-L1-001 のフローティングパレットを状態同期の観点から詳細化する。CR-006 Part 2。
``[P]`` のヘッダー内での並び位置が第 2 要素から第 4 要素へ移っても、本同期制約の内容は
変わらない (位置は TOOL-L1-008 の関心事であり、状態同期は本要求の関心事である)。CR-015。
<<<
VERIFICATION: >>>
パレット側の最小化ボタンで最小化するとヘッダー ``[P]`` が不活性 (色変化) 表示になり、逆にヘッダー
``[P]`` から最小化してもパレット側最小化ボタンの表示状態が追従して、両者が常に同一の最小化状態を
指すことを確認すること。
<<<
RELATIONS:
- TYPE: Parent
  VALUE: TOOL-L1-001

[REQUIREMENT]
UID: TOOL-L2-009
TYPE: Non-Functional
PRIORITY: Should
LAYER: L2_Component
TITLE: パレットのアイコン体系 (キャンバスと同一の形状定義・線画・配置・比率)
STATEMENT: >>>
フローティングパレット (TOOL-L1-001) のアイコン体系は、次を満たすこと。

規則 (1) 形状の単一の正: パレットが表示するタスク形状・マイルストーン形状 (CR-004 の 7 種特殊
マイルストーンを含む) のアイコンは、キャンバス描画が用いるのと同一の形状定義 (同一の
パスビルダー) から生成すること。パレット専用の第 2 の形状定義 (文字グリフ・絵文字・独自パス)
を持たず、キャンバス側の形状を変更したときパレット側の見た目が必ず追従すること
(パレットとキャンバスが乖離し得ないこと)。

規則 (2) 線画への統一: パレット内のアイコンから絵文字グリフを廃し、すべて線画 (アウトライン、
テーマ色を継ぐストローク) で描くこと。対象はキャンバスに対応形状を持つ図形アイコンと、
対応形状を持たないコマンドボタン (イナズマ線・コメント追加・枠追加・透かし等) の双方とする。

規則 (3) グループキャプションの削減: イナズマ線ボタンに付されていた ``LINE`` グループキャプションは
表示しないこと (ボタン自体の機能は維持する)。

規則 (4) 配置: シェイプピッカーは TASK グループを MILESTONE グループの左に置くこと ( ``[...]``
展開で現れる特殊マイルストーン群は MILESTONE グループに付随し右側に置く)。

規則 (5) 比率: アイコンボックス・グリフ・グループ間隔・ボタン間隔の寸法は、白銀比 ( 1 : √2 ≒
1 : 1.414 ) の等比ラダーから導出し、個別の場当たり的な px 値を持たないこと。

規則 (6) 外観の継続性: ボタンのクローム (灰色・角丸の下地) は従来のままとし、アクセシブルネーム
( ``aria-label`` / ``title`` ) と内部の形状識別子 ( ``data-shape`` 等) は本要求により変化
しないこと (見た目のみの変更であること)。
<<<
RATIONALE: >>>
パレットが文字グリフ・絵文字で形状を「説明」し、キャンバスが実際の図形を「描く」という二重定義は、
同じ形状の 2 つの正を作り黙って乖離する (例: キャンバスの羽根状バナーをパレットが ``>>`` と
表す)。パレットをキャンバスと同一のパスビルダーから描くことで、形状の正を 1 つに保つ。絵文字は
プラットフォーム依存の描画になり既存の線画と視覚言語が揃わないため線画へ統一する。
マイルストーンの形状種別は今後も増える見込みであり、種類が少なく安定した TASK を左の固定位置に
置くと目的のアイコンを探しやすい。寸法を白銀ラダーから導出するのは、マジックナンバーを排し
比率で説明できる配置にするためである。TOOL-L1-001 のフローティングパレットをアイコン表現の
観点から詳細化する。アイコンの分かりやすさは NFR-L1-005 と整合する。CR-014。
<<<
VERIFICATION: >>>
パレットの各図形ボタンが描画するパスが、キャンバス側の形状ビルダーの出力と一致することを
(パレット固有の期待値をハードコードせず、ビルダーの実行結果との突合により) 確認すること。
パレット内に絵文字グリフが残っていないこと、 ``LINE`` キャプションが表示されないこと、DOM 上
TASK グループが MILESTONE グループより先に現れること、アイコン・間隔の寸法が白銀ラダーの
各段から導出された値であること、ボタンのクローム (灰色・角丸) と ``aria-label`` / ``data-shape``
が本要求の適用前後で変化しないことを確認すること。
<<<
RELATIONS:
- TYPE: Parent
  VALUE: TOOL-L1-001

[REQUIREMENT]
UID: TOOL-L1-002
TYPE: Non-Functional
PRIORITY: Should
LAYER: L1_System
I18N: Yes
TITLE: フォントサイズの 3 段階切替 (S/M/L)
STATEMENT: >>>
本システムは、フォントサイズ設定として離散的な 3 段階を提供し、ヘッダーのフォントサイズ切替
ボタンを ``[S]`` (小) / ``[M]`` (中) / ``[L]`` (大) の表記で表示すること。表示アイコンは
``[A-][A][A+]`` から ``[S][M][L]`` へ改称するが、内部値 fontScale ('S' | 'M' | 'L') は変更しない
(表記のみの変更であり、データ形式・保存 JSON への影響はない)。選択された段階は、セクション
(分類名) ・プロパティパネル・アイテムのコメントの 3 対象へ同一の倍率で一律かつ即時に適用し、
ヘッダーとパレットは対象外 (現状維持) とすること。
<<<
RATIONALE: >>>
情報密度と可読性の両立。フォントサイズは各言語の文字幅・可読性に影響し、多言語 UI 全体に
関わるため i18n 対象とする。アイコン表記 ``[A-][A][A+]`` は拡大縮小の演算子に見え離散 3 段階を
誤認させるため ``[S][M][L]`` へ改称し、適用対象をセクション (分類名) ・プロパティパネル・アイテム
のコメントの 3 種へ限定した (ヘッダー・パレットは現状維持で対象外)。user-order item6.3 (★★)。CR-005。
<<<
VERIFICATION: >>>
ヘッダーのフォントサイズ切替ボタンが ``[S]`` / ``[M]`` / ``[L]`` の表記で表示され ( ``[A-][A][A+]``
ではないこと)、内部値 fontScale が 'S' | 'M' | 'L' のまま不変であること。段階を切り替えると、
セクション (分類名: 大分類/中分類/小分類) ・プロパティパネル・アイテムのコメント本文のフォント
サイズが選択サイズで一貫して変化し、ヘッダー (TOOL-L1-008 のボタン群・タイトル) とパレット
(TOOL-L1-001) のフォントサイズは変化しないことを確認すること。
<<<
RELATIONS:
- TYPE: Parent
  VALUE: STK-L0-022

[REQUIREMENT]
UID: TOOL-L1-008
TYPE: Non-Functional
PRIORITY: Should
LAYER: L1_System
TITLE: ヘッダーのボタン配置順序と各ボタンの意味
STATEMENT: >>>
本システムは、画面上部ヘッダーのボタン群を、左から右へ次の順序で配置し、各ボタンに次の意味
(機能実体) を与えること。ボタン名は意味ある実体を伴う名称とする (言霊命名、user-order item60)。

.. list-table::
   :header-rows: 1
   :widths: 8 22 70

   * - 順
     - ボタン
     - 意味 (機能実体)
   * - 1
     - GR Scheduler +(c)
     - 製品名ロゴと著作権表示。ヘッダーの識別領域であり、ヘッダーの一番左 ( すべてのコントロールより左 ) に置く。
   * - 2
     - タイトル
     - 編集中のプロジェクト名 (文書タイトル) の表示・編集領域。ブランディングの直後 (左から 2 番目) に置き、識別領域を左端 2 要素にまとめる。ダブルクリックによるインライン編集の操作系は TOOL-L2-010 に定める。
   * - 3
     - Fit
     - 全体表示 (fit-to-content)。全アイテムが収まるようズーム/スクロールを自動調整する既存の Fit 機能 (パレット内 View グループの fitButton と同一機能) をヘッダーへ配置したもの。識別領域 (ブランディング・タイトル) の直後、コントロール群の先頭 (左から 3 番目) に置く。
   * - 4
     - P
     - フローティングパレット (TOOL-L1-001) の表示/最小化トグル。押下でパレットの表示と最小化を切り替える。パレット側の最小化ボタン (TOOL-L2-006 の状態同期制約参照) と双方向連動し、最小化時は不活性 (色変化) 表示となる。 ``[Fit]`` の直後 (左から 4 番目) に置く。
   * - 5
     - SS
     - 表示域 (現在のビューポート) の画像をクリップボードへコピーする ( ``navigator.clipboard.write`` / ClipboardItem 経由)。全キャンバスではなく現在見えている範囲のみを対象とし、ファイルダウンロードは行わない (下記 Save の SVG/PNG 全体出力とは役割が別)。用途は表示中の画面をパワーポイント等へ即座に貼り付けること。Clipboard API 非対応・権限拒否時のフォールバック (ダウンロード代替またはエラートースト) は実装フェーズで確定する。
   * - 6
     - Load
     - JSON および MSPDI XML の取込。JSON の Load 時にはオプションで取込内容を「ベースライン扱い」として指定できる (CR-002 のベースライン層連動)。取込データは外部入力として厳格に検証・サニタイズする (IO-L1-006)。
   * - 7
     - Save
     - JSON, MSPDI XML, SVG, PNG の出力。SVG/PNG は全キャンバスを Fix した全体出力であり、SS の表示域クリップボードコピーとは役割が別である。
   * - 8
     - Light
     - テーマをライト (明色) に切り替える。
   * - 9
     - Dark
     - テーマをダーク (暗色) に切り替える。
   * - 10
     - Mono L
     - テーマをモノクロ・ライト (単色・明背景) に切り替える。単色テーマは印刷・色覚配慮向け。
   * - 11
     - Mono D
     - テーマをモノクロ・ダーク (単色・暗背景) に切り替える。単色テーマは印刷・色覚配慮向け。
   * - 12
     - Base V
     - ベースライン参照層を可視 (Visible) にする。CR-002 のベースライン層の表示切替であり、予実表示 (planActualDisplay) とは独立。
   * - 13
     - Base I
     - ベースライン参照層を不可視 (Invisible) にする。Base V と対をなす可視トグル。
   * - 14
     - Undo
     - 直前操作を取り消す (TOOL-L1-004 と同一機能)。
   * - 15
     - Redo
     - 取り消した操作をやり直す (TOOL-L1-004 と同一機能)。
   * - 16
     - AI
     - AI 向けプロンプトと JSON スキーマをクリップボードへコピーする (既存実装)。
   * - 17
     - ?
     - ヘルプを表示する。ヘルプの到達先 (ヘルプのポップアップ/メニュー) に ``Download GR Scheduler`` ボタンを含め、押下で配信されたアプリ本体の単一 HTML ( ``gr-scheduler.html`` ) をダウンロードできること (取得方式・オフライン時の扱いは IO-L1-007)。当ボタンの表示文言は CR-006 の ``[en]`` / ``[jp]`` ロケール切替の対象とする。これはヘッダーのトップレベル要素を追加するものではなく、既存の ``?`` (ヘルプ) 到達動線内の詳細である (ヘッダー要素の並び順は不変)。

テーマは Light / Dark / Mono L / Mono D の 4 種とし、Mono の 2 種は単色テーマ (印刷・色覚配慮)
とする。先頭 2 要素 ( ``GR Scheduler +(c)`` ブランディングとタイトル ) はヘッダーの識別領域であり、
コントロールではない。第 3・第 4 要素 ``[Fit]`` ・ ``[P]`` は CR-006 で新設したヘッダーコントロール
であり、 ``[Fit]`` は既存の全体表示 (fit-to-content) を、 ``[P]`` はフローティングパレット
(TOOL-L1-001) の表示/最小化トグルをヘッダーへ露出したものである。 ``[P]`` はパレット側の最小化状態と
双方向連動する (状態同期の制約は TOOL-L2-006 に定める)。識別領域を最左に置き ``[Fit]`` ・ ``[P]`` を
その直後へ繰り下げる本配置は、CR-006 Part 1・2 が定めた配置 ( ``[Fit]`` ・ ``[P]`` をブランディング
より左＝最左に置く ) を supersede する。各ボタンの意味 (機能実体) は CR-003・CR-006 の確定内容から
変更しない。本要求はボタンの並び順と意味を定めるものであり、
フォントサイズ切替 (TOOL-L1-002) の
``[S][M][L]`` はヘッダーには適用されない (ヘッダー・パレットは対象外・現状維持) 点、Undo/Redo (TOOL-L1-004)・保存ショートカット
Ctrl+S (TOOL-L1-005)・フローティングパレット (TOOL-L1-001) との整合を保つこと。Load/Save の
入出力形式は IO-L1-001 (JSON)・IO-L1-002 (MSPDI XML)・IO-L1-003 (SVG) に対応し、SS は
ファイル出力ではなくクリップボードへの画像コピーである。
<<<
RATIONALE: >>>
ボタン追加のたびにヘッダーが場当たり的に混雑する問題を解消し、配置順と各ボタンの意味を明文化
してヘッダーを最小・一貫に保つ。各ボタン名は意味ある実体を伴わせる (user-order item60)。
CR-003 Part 1、STK-L0-021 (ヘッダー最小化・情報密度最大化)。フォント切替 ``[S][M][L]`` の
ヘッダー非適用への整合は CR-005。使用頻度の高い全体表示を ``[Fit]`` として、パレット
最小化時に居所を見失う問題の対策としてパレット表示/最小化トグル ``[P]`` を新設し、
SS の出力先を PNG ダウンロードからクリップボードへの画像コピー (表示画面をパワーポイント等へ即
貼付) へ改める。CR-006 (Part 1・2・3。SS は CR-003 の PNG ダウンロード定義を supersede する)。
ライブ視覚レビューで、製品名とプロジェクト名という「ここが何か」を示す識別領域より先に操作系が
来る並びが読み順として不自然であるとユーザーが判断したため、識別領域 ( ブランディング・タイトル )
を最左へ戻し ``[Fit]`` ・ ``[P]`` をその直後へ繰り下げる。並び順は単一の定数列を唯一の正とし、
DOM 構築順・テストの期待値をそこから導出することでヘッダーの並びが二重定義されないようにする。
なお起票時にユーザーが述べた ``[R]`` は ``[P]`` の言い間違いであり、 ``[R]`` という新規ボタンは
存在しない (後続作業者が幻のボタンを再導出しないよう明記する)。CR-015。
<<<
VERIFICATION: >>>
ヘッダーが GR Scheduler +(c) → タイトル → Fit → P → SS → Load → Save → Light → Dark → Mono L →
Mono D → Base V → Base I → Undo → Redo → AI → ? の順に並ぶこと ( ``[Fit]`` ・ ``[P]`` が
ブランディング・タイトルより左に来ないこと )。 ``[Fit]`` が全体表示 (fit-to-content)
を起動し、 ``[P]`` がパレットの表示/最小化を切り替え、パレット側の最小化と双方向連動して最小化時
に不活性 (色変化) 表示となること。SS が表示域の画像をファイルダウンロードせずクリップボードへ
コピーすること ( ``navigator.clipboard.write`` 経由)。Load が JSON/XML を取り込み (JSON はベース
ライン扱い指定可)、Save が JSON/XML/SVG/PNG を出力し SVG/PNG が全体 Fix 出力であること。テーマ
が 4 種で切り替わり、Base V/I でベースライン層の表示/非表示が切り替わり、AI がプロンプト+JSON
スキーマをクリップボードへコピーすることを確認すること。
<<<
RELATIONS:
- TYPE: Parent
  VALUE: STK-L0-021

[REQUIREMENT]
UID: TOOL-L2-008
TYPE: Non-Functional
PRIORITY: Should
LAYER: L2_Component
I18N: Yes
TITLE: ヘルプ画面のワンスクリーン収まり (3 段組み維持・幅拡大優先・フォント微縮は最終手段)
STATEMENT: >>>
TOOL-L1-008 の第 17 要素 ``?`` (ヘルプ) が開くヘルプ画面は、英語 (en) 表示・日本語 (ja) 表示の
いずれであっても、全内容 (全セクション・全項目) を 1 画面内に縦スクロールなしで収めること。
その際、3 段組みレイアウト ( ``column-count: 3`` 相当) を維持し、1 列/2 列への縮退・タブ/アコー
ディオン等の別 UI パラダイムへの置換・縦スクロールの導入のいずれも行わないこと。表示幅は利用
可能なビューポート領域まで最大化すること (現行 ``85vw`` 相当からの拡大、または余白/ガター縮小に
より実質表示幅を広げる)。フォントサイズの縮小は最終手段とし、幅の最大化のみでは収まらない場合
に限り、可読性を保つ範囲でわずかに縮小すること (段組み崩し・スクロール導入はフォント微縮より
優先度が低く、最後の手段としても採らない)。本制約は CR-006 の ``[en]`` / ``[jp]`` ロケール切替に
よる表示文言変更後、および CR-010 の ``Download GR Scheduler`` ボタン追加後のヘルプ内容量に
おいても満たすこと。CR-011。
<<<
RATIONALE: >>>
ヘルプは一覧性 (全項目を一望できること) が価値であり、縦スクロールや段組み崩しは俯瞰性を
損なう。多言語化 (CR-006 の日英切替) や到達動線へのボタン追加 (CR-010) により内容量・文字幅が
増えても一覧性を保つため、幅の最大化を第一手段とし、フォント微縮を可読性を損なわない最終手段
に限定する。TOOL-L1-008 の第 17 要素 ``?`` (ヘルプ) のレイアウト制約としての詳細化。
user-order item6 (アフォーダンス・マニュアル不要)、CR-011。
<<<
VERIFICATION: >>>
en 表示・ja 表示のいずれでもヘルプ画面の全内容 (全セクション・全項目) が縦スクロールなしで
1 画面に収まること、レイアウトが 3 段組みで維持される (1 列/2 列化・タブ/アコーディオン化・
スクロール導入が生じない) こと、表示幅が現行 ``85vw`` 相当より利用可能領域まで拡大されること、
フォント縮小が幅最大化のみでは収まらない場合に限り可読性を保つ範囲で適用されることを確認する
こと。CR-006 の ``[en]`` / ``[jp]`` 切替後・CR-010 の ``Download GR Scheduler`` ボタン追加後の
内容量でも同制約が満たされることを確認すること。
<<<
RELATIONS:
- TYPE: Parent
  VALUE: TOOL-L1-008

[REQUIREMENT]
UID: TOOL-L2-010
TYPE: Functional
PRIORITY: Should
LAYER: L2_Component
WCAG: AA
I18N: Yes
TITLE: プロジェクトタイトルのインライン編集 (ダブルクリック・Enter 確定・Escape 取消・Undo 可能・role 提示・プレースホルダ i18n)
STATEMENT: >>>
TOOL-L1-008 の第 2 要素であるタイトル表示領域は、ヘッダー上でプロジェクト名 (
``ScheduleDocument.title`` ) をインライン編集できること。操作系は次のとおりとし、コメントの
ダブルクリック編集 (CR-007 Part 3) の先例に倣う。

操作 (1) 起動: タイトルをダブルクリックすると、その場でテキスト編集モードへ入る。

操作 (2) 確定: Enter で入力内容を ``ScheduleDocument.title`` へ確定する。確定は Undo 可能な
コマンドとして発行し (TOOL-L1-004)、Undo で編集前のタイトルへ、Redo で編集後のタイトルへ戻ること。

操作 (3) 取消: Escape で入力内容を破棄し編集前の表示へ復元する ( ``title`` を変更しない)。
確定と取消はいずれか一方だけが 1 回起こり、二重確定・確定後の取消は生じないこと。

操作 (4) 表示の追従: ヘッダーのタイトル表示は、初期表示・Import 時だけでなく、ドキュメント変更の
通知を購読して継続的に追従すること。すなわち編集による確定・Undo・Redo・文書全体の差し替え
(Load / New) のいずれでも、ヘッダーが現在の ``title`` を表示すること。購読は 1 回のみ登録し
二重描画を生じさせないこと。編集中は購読による再描画で入力中テキストが失われないこと。

操作 (5) 空タイトルの代替表示: ``title`` が空 (空白のみを含む) のとき、ヘッダーはプレースホルダ
文字列を表示すること。プレースホルダは製品名や既定テンプレート名と紛れない文字列とし、
初期構築時と変更追従時の双方が同一の定義を参照すること (代替文字列を二重に定義しない)。

操作 (6) 支援技術への役割の提示: 編集していない状態のタイトル表示要素は、支援技術に対して、
活性化するとスケジュール名を変更できる操作要素であることが伝わる役割 (role) を提示すること。
フォーカスを受け取れるだけの装飾 ( ``tabindex`` の付与のみで role を持たない要素) では
「ただのテキスト」としてしか伝わらず不足であり、WCAG 2.1 AA の 4.1.2 (Name, Role, Value) に
反するため許容しない。実現方法は実装時に選べる (適切な role の明示、または実際のボタン要素の
採用のいずれでもよい) が、いずれの場合も、その要素が何をするものかを述べるアクセシブル名を
併せて提示すること。編集モードで表示される入力要素にも、同様にアクセシブル名を与えること。
役割・名称の提示は識別子 ( ``data-role`` 等) とは独立の関心事であり、識別子は英語 ASCII の
ままとする。

操作 (7) プレースホルダの多言語化: 操作 (5) のプレースホルダ文字列は i18n 対象とし、UI 言語
( ``activeLocale`` 、PROP-L1-003) に追従して表示を切り替えること。多言語化にあたっても操作 (5)
の単一定義の制約は維持し、ロケールごとの文言を 1 か所 (メッセージ定義) にのみ持つこと。
局所化の対象は画面に出る表示文字列に限り、定数名・ ``data-role`` 等の識別子は英語 ASCII の
ままとする。同じ制約をアクセシブル名 (操作 (6)) にも適用し、表示される文言は ``activeLocale``
に追従すること。
<<<
RATIONALE: >>>
プロジェクト名は文書の第一の識別子でありながら、変更する手段がヘッダーに無かった。編集を
ヘッダー上のインライン操作にすると、表示している当のものを直接直せる (POLA)。操作系を
コメント編集と揃えるのは、同じ「その場編集」の身振りをアプリ内で 1 つに保つためである。
確定を Undo 可能なコマンドとするのは、タイトルが永続ドキュメント値であり他の編集と同じ
取り消し規約に従うべきだからである。表示を都度の呼び出しではなく購読で追従させるのは、
Import 以外の経路 (編集・Undo/Redo・文書差し替え) でもヘッダーとモデルが必ず一致するように
するためであり、これは DEF-010 (ヘッダー表示がモデルと連動して見えない) の解消でもある。
空タイトルの代替文字列を製品名と異なるものにするのは、「タイトルが表示されているのか既定
文字列なのか」をユーザーが区別できるようにするためである。CR-016。
操作 (6) と操作 (7) は DEF-012 の是正である。CR-016 で新設した本要求は、見えるユーザーに対する
操作系 (ダブルクリック編集) だけを規定し、支援技術に対する役割の提示と、プレースホルダの
多言語化を規定していなかった。 role を持たずフォーカスだけ受け取る要素は、支援技術には
「編集できない静的テキスト」としてしか露出せず、キーボードで到達できても何が起きるか分からない。
本プロジェクトは品質目標として WCAG 2.1 AA を有効化しているため、これは改善提案ではなく
要求違反であり、要求として明記する (4.1.2 Name, Role, Value)。役割の具体的な実現方法を
実装に委ねるのは、要求が定めるべきは「支援技術に何が伝わるか」であって DOM の実現手段ではない
ためである。プレースホルダを i18n 対象とするのは、CLAUDE.md が製品 UI の表示文字列を i18n 対象と
定めており、ヘッダーの空タイトル表示だけが英語固定で取り残されると、日本語表示のユーザーに
英語リテラルが露出するためである。単一定義の制約 (操作 (5)) を維持したまま多言語化するのは、
文言をロケール別に散在させると SSOT が崩れ、初期構築時と変更追従時で別々の文字列が出る旧来の
不具合を再発させるためである。識別子を英語 ASCII に留めるのは、局所化すべきは表示文字列のみで
あり、 ``data-role`` 等の契約面はテストと実装の共通語だからである。DEF-012。
<<<
VERIFICATION: >>>
ヘッダーのタイトルをダブルクリックすると編集モードへ入り、Enter で ``ScheduleDocument.title``
が更新されヘッダー表示が即座に追従すること、Escape で入力が破棄され ``title`` が変化しない
こと、確定した変更が Undo で元に戻り Redo で再適用されること、Undo/Redo・文書差し替え
(Load / New) の後もヘッダー表示が現在の ``title`` と一致すること、編集中に発生した変更通知で
入力中テキストが消えないこと、 ``title`` が空のときプレースホルダ文字列が表示され、それが
既定テンプレートの実際のタイトルと区別できることを確認すること。
加えて、編集していない状態のタイトル表示要素が支援技術に対して操作要素としての役割を提示し、
その要素が行う操作 (スケジュール名の変更) を述べるアクセシブル名を持つこと、編集モードの入力
要素にもアクセシブル名があること、自動チェック (axe) で WCAG 2.1 AA の 4.1.2 に関する violation
が検出されないことを確認すること。キーボードのみでタイトルの編集開始・確定・取消が行えること。
また ``title`` が空の状態で UI 言語を切り替えると、プレースホルダ表示が ``activeLocale`` に
追従して切り替わること、その文言の定義が 1 か所のみであること (初期構築時と変更追従時が同一の
定義を参照すること)、定数名・ ``data-role`` 等の識別子が英語 ASCII のまま変化しないことを
確認すること。
<<<
RELATIONS:
- TYPE: Parent
  VALUE: TOOL-L1-008
- TYPE: Parent
  VALUE: CANVAS-L1-004

[[/SECTION]]

[[SECTION]]
TITLE: 2. 編集効率化 (Copy/Paste, Undo/Redo, Shortcuts)

[REQUIREMENT]
UID: TOOL-L1-003
TYPE: Functional
PRIORITY: Should
LAYER: L1_System
TITLE: アイテムのコピー&ペースト
STATEMENT: >>>
本システムは、選択したマイルストーン/タスクをコピーし、指定位置へペーストして、
プロパティ (略称・色・線幅・図形等) を引き継いだ複製を生成すること。
<<<
RATIONALE: 類似アイテムの入力負荷を下げる。user-order item13。
VERIFICATION: 1 個以上のアイテムをコピー後ペーストすると、元のプロパティを保持した複製が新規 UID で生成されること。
RELATIONS:
- TYPE: Parent
  VALUE: STK-L0-008

[REQUIREMENT]
UID: TOOL-L1-004
TYPE: Functional
PRIORITY: Should
LAYER: L1_System
TITLE: 操作の取り消し/やり直し (Undo/Redo)
STATEMENT: >>>
本システムは、アイテムの作成・移動・リサイズ・削除・プロパティ編集等の操作を取り消し (Undo)
でき、取り消した操作をやり直し (Redo) できること。
<<<
RATIONALE: 誤操作からの安全な回復。パワポ/Excel 代替として不可欠。user-order item53、STK-L0-008 (Undo/Redo)。
VERIFICATION: 任意の編集操作の後に Undo で直前状態へ戻り、Redo で操作後状態へ復元できること。連続 Undo/Redo が履歴順に機能すること。
RELATIONS:
- TYPE: Parent
  VALUE: STK-L0-008

[REQUIREMENT]
UID: TOOL-L1-005
TYPE: Functional
PRIORITY: Should
LAYER: L1_System
TITLE: ショートカットキー
STATEMENT: >>>
本システムは、主要な編集・表示操作をキーボードショートカットで実行でき、少なくとも次の
代表キー割当を提供すること。

.. list-table::
   :header-rows: 1
   :widths: 34 66

   * - キー
     - 動作
   * - Ctrl+Z
     - 元に戻す (Undo)
   * - Ctrl+Y / Ctrl+Shift+Z
     - やり直し (Redo)
   * - Ctrl+C
     - コピー
   * - Ctrl+V
     - ペースト
   * - Ctrl+A
     - 全選択 (アイテム + コメント)
   * - Ctrl+S
     - ファイル保存 (.json)
   * - Delete
     - 選択アイテムの削除
   * - 方向キー
     - 選択アイテムの微小移動
   * - Ctrl + ホイール
     - ズーム

``Ctrl+A`` の全選択は、アイテムだけでなくコメントも選択対象に含めること。これは選択モデル
(SEL-L1-001 / SEL-L1-002 の矩形選択・ ``Ctrl+click`` 増減を含む) がコメントを選択可能な対象として
扱うことを前提とする。コピー&ペースト (Ctrl+C / Ctrl+V) はアイテムのコピー&ペースト (TOOL-L1-003)
と対応する。
<<<
RATIONALE: マウス往復を減らし操作を高速化する。割当一覧はユーザーレビュー対象 (interview-record 7)。user-order item53。 ``Ctrl+A`` の全選択にコメントを含める規定と選択モデルがコメントを選択対象として扱う前提は CR-007 Part 4。
VERIFICATION: 上表の各キーが対応動作を起動し、テキスト入力中は文字入力が優先されること。 ``Ctrl+A`` を押すとアイテムとコメントの両方が全選択されることを確認すること。
RELATIONS:
- TYPE: Parent
  VALUE: STK-L0-008

[REQUIREMENT]
UID: TOOL-L1-006
TYPE: Non-Functional
PRIORITY: Should
LAYER: L1_System
TITLE: パレット非選択時の透明化
STATEMENT: >>>
本システムは、ツール操作用パレットが選択・操作されていない間、パレットを薄く透明表示とし、
ポインタをパレットへ重ねた際に不透明へ戻すこと。
<<<
RATIONALE: 非操作時にキャンバス視認を妨げず、描画面積を最大化する。user-order item58。
VERIFICATION: 一定時間パレットを操作しないとパレットが半透明化し、ホバー/操作で不透明へ復帰すること。
RELATIONS:
- TYPE: Parent
  VALUE: STK-L0-019

[[/SECTION]]

[[SECTION]]
TITLE: 3. 透かし (Watermark)

[REQUIREMENT]
UID: TOOL-L1-007
TYPE: Functional
PRIORITY: Must
LAYER: L1_System
TITLE: 日程表への透かし付与
STATEMENT: >>>
本システムは、日程表の表示および SVG 出力に透かしを重ねて付与できること。
<<<
RATIONALE: Web 会議で秘密の日程を無断キャプチャされた際の証跡を残す。user-order item59。
VERIFICATION: 透かしを有効にすると、キャンバス表示と SVG 出力の双方に透かし層が付与されること。
RELATIONS:
- TYPE: Parent
  VALUE: STK-L0-013

[REQUIREMENT]
UID: TOOL-L2-001
TYPE: Functional
PRIORITY: Must
LAYER: L2_Component
TITLE: 透かしの内容 (ローカル入力ユーザー名 + UTC 時刻・必須)
STATEMENT: >>>
透かしコンポーネントは、透かし文字列にローカル入力ユーザー名と UTC 時刻を含めること。
UTC 時刻は必須要素であり、ユーザー名のみの表示は許さず、常に UTC 時刻を伴わせること
(空タイムスタンプを許容しない)。サーバー認証を持たないため、ユーザー名はローカルで
入力/保持する名称を用いること。UTC 時刻の表示形式は TOOL-L2-004、更新タイミングは
TOOL-L2-007 に従うこと。CR-009。
<<<
RATIONALE: >>>
証跡には「誰が・いつ」を残す必要がある。UTC 時刻を任意ではなく必須とすることで、
ユーザー名のみで時刻を欠いた証跡不十分な透かしが生成される事故を防ぐ。user-order item59.1、CR-009。
<<<
VERIFICATION: 生成された透かしに、設定済みのローカルユーザー名と UTC の ISO 8601 形式の時刻が常に (時刻が空でなく) 含まれることを確認すること。
RELATIONS:
- TYPE: Parent
  VALUE: TOOL-L1-007

[REQUIREMENT]
UID: TOOL-L2-002
TYPE: Functional
PRIORITY: Must
LAYER: L2_Component
TITLE: 透かしの配置 (斜め方向・薄い複数タイル)
STATEMENT: >>>
透かしコンポーネントは、透かしを斜め方向に傾け、画面全体を覆うよう薄い複数タイルとして
繰り返し配置すること。
<<<
RATIONALE: 部分キャプチャや切り抜きでも透かしが必ず含まれるようにする。user-order item59.2。
VERIFICATION: 透かしが一定角度で傾き、低い不透明度でキャンバス全面にタイル状に反復配置されること。
RELATIONS:
- TYPE: Parent
  VALUE: TOOL-L1-007

[REQUIREMENT]
UID: TOOL-L2-003
TYPE: Functional
PRIORITY: Must
LAYER: L2_Component
TITLE: 透かしの表示/非表示切替
STATEMENT: >>>
透かしコンポーネントは、透かしの表示と非表示をユーザー操作で切り替えられること。
<<<
RATIONALE: 共有時のみ証跡を付け、編集時は視認性を優先できるようにする。user-order item59.3。
VERIFICATION: 表示/非表示を切り替えると、キャンバスおよび SVG 出力への透かし付与が即時に反映されること。
RELATIONS:
- TYPE: Parent
  VALUE: TOOL-L1-007

[REQUIREMENT]
UID: TOOL-L2-004
TYPE: Functional
PRIORITY: Must
LAYER: L2_Component
TITLE: 透かしの既定表示 (既定オン・既定文字列・薄さ)
STATEMENT: >>>
透かしコンポーネントは、初期状態で透かしを表示 (既定オン) とし、既定の透かし文字列を
``GoodRelax`` とすること。透かしの不透明度は、内容が判読できる範囲で従来より薄い値
(0.06) とすること。透かしの日時は必須表示であり、UTC の ISO 8601 形式 (末尾 ``Z`` 、
分精度、例: ``2026-07-19T05:12Z`` ) で表示すること。既定表示 (既定オン・既定文字列
``GoodRelax`` ・不透明度 0.06) においても常に有効な UTC 時刻を伴わせ、空タイムスタンプ
を許容しないこと。CR-009。
<<<
RATIONALE: >>>
既定で証跡を残し、うっかり無透かしで共有される事故を防ぐ。既定文字列と薄さは視認性と
非妨害の両立。日時は時差非依存の UTC で一意化し、任意ではなく必須とすることで既定表示
でも時刻の欠けた証跡が生じないようにする。user-order item59.1 / item59、CR-009。
<<<
VERIFICATION: >>>
新規文書で透かしが既定表示となり、文字列が ``GoodRelax`` 、不透明度が 0.06 であること、
透かしの日時が常に (空でなく) UTC ISO 8601 (分精度・末尾 Z) で描画されることを確認すること。
<<<
RELATIONS:
- TYPE: Parent
  VALUE: TOOL-L1-007

[REQUIREMENT]
UID: TOOL-L2-005
TYPE: Functional
PRIORITY: Must
LAYER: L2_Component
TITLE: 透かし非表示のパスワード保護 (ハッシュのみ保存)
STATEMENT: >>>
透かしコンポーネントは、透かしの非表示化にパスワードを要求すること。入力パスワードは
SHA-256 (Web Crypto ``crypto.subtle`` ) でハッシュ化し、保存済みハッシュと一致した場合の
み非表示にすること。文書・モデル・出力 (HTML+JSON) には生パスワードを一切保存せず、
ハッシュのみを保持すること。

既定パスワードは ``GoodRelax`` とし、その SHA-256 (16 進) を既定ハッシュとして定数
``DEFAULT_WATERMARK_HIDE_PASSWORD_HASH`` (コード/モデル) に保持する。SHA-256 ハッシュ値
そのものは実装フェーズで ``crypto.subtle`` により算出し当該定数へ設定する (誤記防止のため
本仕様書にはハッシュ値を記載しない)。この既定パスワードはサーバー配備時のローテーション用の
記録であり、サーバー配備時には必ず変更すること。CR-009。

なお本製品はクライアント単体の単一 HTML アプリであるため、パスワードによる非表示は
弱い抑止 (soft deterrent) に留まる。DOM/HTML を直接編集すれば透かしは除去され得る。
生パスワードを保存せずハッシュのみを保持し、既定値をサーバーローテーション用に記録するのは
正しい運用だが、クライアントでは暗号的に強制できない点に留意すること。
<<<
RATIONALE: >>>
証跡を安易に外せないようにしつつ、生パスワードの漏洩を避ける。ハッシュ比較で最小限の
抑止を提供する。user-order item59.3。
<<<
VERIFICATION: >>>
誤ったパスワードでは透かしが表示のまま、正しい既定パスワード ``GoodRelax`` では
非表示になること、出力 (JSON/HTML) に生パスワードが現れず ``DEFAULT_WATERMARK_HIDE_PASSWORD_HASH``
のハッシュ値のみが含まれることを確認すること。
<<<
RELATIONS:
- TYPE: Parent
  VALUE: TOOL-L2-003

[REQUIREMENT]
UID: TOOL-L2-007
TYPE: Functional
PRIORITY: Must
LAYER: L2_Component
TITLE: 透かし UTC 時刻の更新タイミング (文書内容変更時のみ)
STATEMENT: >>>
透かしコンポーネントは、透かしの UTC 時刻を、文書の内容 (アイテム・マイルストーン・
依存線・セクション・注釈等の永続ドキュメント値) が変更されたタイミングでのみ現在の
UTC 時刻へ再採番すること。Undo/Redo による内容変更も再採番の対象に含めること。
一方、ビューポート操作すなわちズーム・パン・スクロール ( ``zoomX`` / ``zoomY`` /
``scrollX`` / ``scrollY`` 等の表示専用状態) では再採番せず、また透かしの表示/非表示
トグル (TOOL-L2-003、 ``viewState.watermark.enabled`` の変更) 単体でも再採番しない
(いずれの場合も直近の内容変更時点の UTC 時刻を保持すること)。実装上の結線点は
コマンドスタック ( ``ScheduleStore`` の ``dispatch`` / ``undo`` / ``redo`` ) とし、
これらで永続ドキュメントが変化した直後に再採番する (DEC-005 決定 3)。CR-009。
<<<
RATIONALE: >>>
「いつ時点の内容の透かしか」を証跡として正確にするため、UTC 時刻を内容 (アイテム) の
変更へ連動させる。ズーム・スクロール等の表示操作は内容を変えないため時刻を書き換えず、
証跡を「常に今」に見せかけることを避ける。結線点をコマンドスタックに限定することで
ビューポート操作・表示トグルの誤発火を防ぐ。DEC-005 決定 3、CR-009。
<<<
VERIFICATION: >>>
アイテム/マイルストーン/依存線/セクション/注釈を変更 (Undo/Redo を含む) すると透かしの
UTC 時刻が変更直後の現在時刻へ更新されること、ズーム・パン・スクロールのみの操作では
UTC 時刻が更新されないこと、透かしの表示/非表示トグル単体でも UTC 時刻が更新されず
直近の内容変更時刻を保持することを確認すること。
<<<
RELATIONS:
- TYPE: Parent
  VALUE: TOOL-L2-001

[[/SECTION]]
