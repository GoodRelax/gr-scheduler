[DOCUMENT]
TITLE: gr-scheduler 要求仕様 - 依存関係 (L1-L3)

[GRAMMAR]
IMPORT_FROM_FILE: gr-scheduler-grammar.sgra

[TEXT]
STATEMENT: >>>
本書は gr-scheduler の依存関係ドメイン (プレフィクス DEP) のシステム要求 (L1) と
コンポーネント要求 (L2) を定義する。マイルストーン/タスク間の依存を、アイコンの
9 点アンカーから引き出し/引き入れる線で表現し、他アイコンとの重なりを避けて自動配線し、
折れ点を 0〜3 に収める。各 L1 要求はステークホルダ要求 STK-L0-010 (依存関係の可視化) を
Parent で詳細化する。出典は `user-order.md` item33 (= coverage 表の item34 系列) と
`01-stakeholder-requirements.sdoc`。
<<<

[[SECTION]]
TITLE: 1. 依存関係の表現 (Dependency Representation)

[REQUIREMENT]
UID: DEP-L1-001
TYPE: Functional
PRIORITY: Must
LAYER: L1_System
TITLE: マイルストーン/タスク間の依存関係を線で表現する
STATEMENT: >>>
本システムは、2 つのマイルストーン/タスクを始点アイテムと終点アイテムとして選び、
その間に有向の依存線を 1 本引いて依存関係を表現できること。
<<<
RATIONALE: >>>
影響波及 (どのタスクが遅れると何が遅れるか) を一枚絵の上で可視化する中核機能。
user-order item34。
<<<
VERIFICATION: >>>
任意の 2 アイテムを指定して依存線を作成すると、始点から終点へ向きを持つ 1 本の線が
描画され、依存関係のデータ (始点 UID・終点 UID) が内部モデルに保持されること。
<<<
RELATIONS:
- TYPE: Parent
  VALUE: STK-L0-010

[[/SECTION]]

[[SECTION]]
TITLE: 2. 9 点アンカーからの引き出し/引き入れ (9-Point Anchors)

[REQUIREMENT]
UID: DEP-L1-002
TYPE: Functional
PRIORITY: Must
LAYER: L1_System
TITLE: 依存線を 9 点アンカーから引き出し/引き入れる
STATEMENT: >>>
本システムは、アイテムのアイコン/タスクバー形状上の 9 点 (四辺の中点 4 点・四隅 4 点・
中央 1 点) をアンカーとして幾何的に定義し、線の両端をそのアンカー座標へ正確に終端させる
こと。ただし CR-003 (承認 2026-07-20) Part 3 により、当面は始点/終点アンカーの手動選択を
用いず、配線は DEP-L1-003 の決定的自動配線規則 (始点=先行アイテムの右辺中点 middle_right、
終点=後続アイテムの左辺中点 middle_left) で決定する。9 点アンカーの座標定義自体は将来の
手動選択復活に備えて本要求に保持する。
<<<
RATIONALE: >>>
線端がアイテムから浮かず、アイテム形状の意味のある点に吸着することで、依存の起点/終点が
一目で分かる (モックのフィードバック: 線端はアイテムに必ず接続すること)。9 点は
アイコン/タスクバーのバウンディングボックス上に幾何的に定義する。CR-003 では手動選択面を
簡素化し、現行は right-edge 出/left-edge 入の 2 点 (middle_right / middle_left) を用いるが、
9 点の座標定義は将来の手動選択に備えて保持する。user-order item34.1、CR-003 Part 3。
<<<
VERIFICATION: >>>
下表の 9 アンカーそれぞれについて、そのアイテム形状上の座標が定義どおり (相対座標 × 幅/高さ)
に算出され (許容誤差 1px 以内)、アイテムを移動しても各アンカー座標が形状に追従すること。
現行の自動配線では始点に middle_right、終点に middle_left が用いられ、線端が当該アンカー座標へ
接続を維持することを単体テストおよび描画計測で確認すること。
<<<
RELATIONS:
- TYPE: Parent
  VALUE: STK-L0-010

[TEXT]
STATEMENT: >>>
9 点アンカーは、アイテムのバウンディングボックス (幅 w・高さ h、左上原点) 上に次のとおり
定義する。行/列の中点は 0.5、端は 0 と 1 で表す。

.. list-table::
   :header-rows: 1
   :widths: 8 22 20 50

   * - No
     - アンカー名
     - 相対座標 (x, y)
     - 位置の説明
   * - 1
     - top_left
     - (0, 0)
     - 左上角
   * - 2
     - top_center
     - (0.5, 0)
     - 上辺中点
   * - 3
     - top_right
     - (1, 0)
     - 右上角
   * - 4
     - middle_left
     - (0, 0.5)
     - 左辺中点
   * - 5
     - center
     - (0.5, 0.5)
     - 中央
   * - 6
     - middle_right
     - (1, 0.5)
     - 右辺中点
   * - 7
     - bottom_left
     - (0, 1)
     - 左下角
   * - 8
     - bottom_center
     - (0.5, 1)
     - 下辺中点
   * - 9
     - bottom_right
     - (1, 1)
     - 右下角

.. raw:: html

    <pre class="mermaid">
    flowchart LR
        subgraph ITEM["Item bounding box (w x h)"]
            A1["1 top_left"]
            A2["2 top_center"]
            A3["3 top_right"]
            A4["4 middle_left"]
            A5["5 center"]
            A6["6 middle_right"]
            A7["7 bottom_left"]
            A8["8 bottom_center"]
            A9["9 bottom_right"]
        end
        A6 -->|"draw out / draw in"| A4
    </pre>
<<<

[[/SECTION]]

[[SECTION]]
TITLE: 3. 重なり回避の自動配線 (Overlap-Avoiding Auto Routing)

[REQUIREMENT]
UID: DEP-L1-003
TYPE: Functional
PRIORITY: Must
LAYER: L1_System
TITLE: 依存線を他アイコンとの重なりを避けて自動配線する
STATEMENT: >>>
本システムは、依存線を決定的な直交 (矩形) 経路で自動配線すること。CR-003 (承認 2026-07-20)
Part 3 により、すべての依存線は先行 (始点) アイテムの右辺から出る。CR-008 (承認 2026-07-21)
Part 1 により、すべての依存線は、先行の出口直後と後続の入口直前の双方に、矢じり先端の 2 倍
( ``CONNECTOR_STUB_PX`` ) の短い水平スタブを必ず備えること。この水平スタブは、ズームレベルや
アイテムの重なり方 (前進・後方・同一行隣接のいずれ) に依らず確実に確保する。後続の左辺から
入る通常経路では左辺の直前が、後続の上端/下端から入る経路 (下記) でも入口直前が、必ず水平
セグメントで終端し、矢印が水平に入ること。垂直セグメントのまま矢じりへ突入する経路
(CR-008 で上書きする IM8 の上下端入線がこれに該当) は禁止する。後続が先行より下にある場合は、
右へ出た直後に下へ折れて降下し、後続の左辺へ入る。後続が先行より上にある場合は、右へ可能な
限り (後続のすぐ手前まで) 進み、後続の直前で上へ折れて後続の左辺へ入る。後続が先行と水平方向に
重なり上下に積まれている (別レーン) 場合、または後続の左辺が先行の右辺より左に位置し左辺入では
先行を跨いで左へ遡ってしまう場合は、左辺入に代えて後続の上端 (後続が下) または下端 (後続が上)
から侵入する。この上下端入線でも、入口直前に水平スタブを設けて矢印を水平に後続 facing edge
近傍へ入れる。侵入列は先行の右辺出口より左に置かず、経路が先行の出口 x より左へ進まないこと。
後続が同一行の直後に隣接し左辺入が退化する場合は、行の下 (または上) へスタブ 1 本分迂回して
後続へ入るが、CR-008 Part 2 により、依存の向き (先行→後続) が視覚的に正しく読める経路とし、
逆向きに見える U 字ルート (Concept→Series Development のように後続から先行へ向かって見える形状)
を禁止する。折れ点数の上限は DEP-L2-002 に従う (前進=0〜3、重なり/後方/同一行連続=最大 4)。
始点/終点アイテムの移動時には経路を再計算すること。
<<<
RATIONALE: >>>
線が他アイコンの上を横切ると依存関係も背後のアイテムも読めなくなる。CR-003 では手動アンカー
選択を廃し、右出/左入・直交・上下折れ・行間ギャップという決定的規則へ簡素化することで、配線
結果を予測可能かつ可読に保つ (モックのフィードバック: 線は他アイテムと極力重ならないこと)。
CR-008 では、IM8 の上下端入線 (水平スタブ無し) が矢印手前に水平部を持たず入線方向が読み取り
にくく、一部ケースで依存の向きが逆に見えた実データ不具合を受け、出口/入口の水平スタブを必須化し、
視認方向の正しさを設計方針として確定する。配線アルゴリズムの詳細は DEP-L2-001 で、折れ点数の
上限は DEP-L2-002 で定義する。user-order item34.2、CR-003 Part 3、CR-008。
<<<
VERIFICATION: >>>
後続が下/上/水平重なり/同一行連続の各配置で依存線を自動描画し、(1) 線が先行の右辺から出て
後続へ入ること、(2) 先行の出口直後と後続の入口直前の双方に矢じり先端の 2 倍
( ``CONNECTOR_STUB_PX`` ) の水平スタブが存在し、上下端入線ケースでも入口直前が水平で終端し矢印が
水平に入ること (垂直のまま矢じりへ突入する経路が無いこと)、(3) 後続が下では出直後に下折れ、
後続が上では後続直前で上折れすること、(4) 水平に重なり上下に積まれた配置では横移動が両バーを
跨がず行間ギャップを通ること、(5) 同一行連続ケースで依存の向き (先行→後続) が視覚的に正しく
読め、逆向きに見える U 字ルートが無いこと、を単体テストおよび描画計測で確認すること。
<<<
RELATIONS:
- TYPE: Parent
  VALUE: STK-L0-010

[REQUIREMENT]
UID: DEP-L2-001
TYPE: Non-Functional
PRIORITY: Must
LAYER: L2_Component
TITLE: 依存線ルーティングエンジンの障害物回避直交配線
STATEMENT: >>>
依存線ルーティングエンジンは、水平/垂直セグメントからなる直交経路 (orthogonal routing) で
依存線を配線すること。CR-003 (承認 2026-07-20) Part 3 により、始点アンカーを先行アイテムの
右辺中点 (middle_right) に固定し、DEP-L1-003 の決定的規則 (右出、後続が下なら出直後に下折れ、
後続が上なら後続直前で上折れ、上下積みの水平重なりでは横移動を行間ギャップに通す) に従って
経路を生成すること。CR-008 (承認 2026-07-21) Part 1 により、経路は先行の出口直後と後続の
入口直前の双方に、矢じり先端の 2 倍 ( ``CONNECTOR_STUB_PX`` ) の水平スタブを必ず含み、いずれの
入口も水平セグメントで終端して矢印が水平に入ること (垂直のまま矢じりへ突入する経路は不可)。
他アイテムのバウンディングボックスは障害物として扱い、上記決定的経路の範囲で中間アイテムとの
重なりを避けること。後続が上下に積まれ/水平に重なる、または同一行の直後に隣接するケースでは、
左辺中点入に代えて後続の上端/下端から侵入する経路へ切替えるが、その入口直前にも水平スタブを
設けること。同一行連続ケースでは、CR-008 Part 2 により依存の向き (先行→後続) が視覚的に正しく
読める経路とし、逆向きに見える U 字ルートを生成しないこと。折れ点数は DEP-L2-002 に従う
(前進=0〜3、重なり/後方/同一行連続=最大 4)。
<<<
RATIONALE: >>>
自動配線 (DEP-L1-003) の内部アルゴリズム。CR-003 では始点/終点を右辺中点/左辺中点に固定した
決定的な直交配線へ specialize する。障害物回避は決定的経路 (行間ギャップの利用等) で行い、汎用の
格子探索よりも予測可能な結果を優先する。CR-008 では、出口/入口の水平スタブ必須化と視認方向の
正しさを配線規則へ組み込み、IM8 の上下端入線 (水平スタブ無し・逆向きに見える U 字) を上書き
する。直交配線は折れ点数の制御 (DEP-L2-002) とも整合する。user-order item34.2、CR-003 Part 3、
CR-008。
<<<
VERIFICATION: >>>
既知の先行/後続配置 (後続が下・上・水平重なり・同一行連続の各ケース) を入力にルーティング
エンジンを実行し、出力経路が始点=middle_right で開始し、先行の出口直後と後続の入口直前の双方に
矢じり先端の 2 倍 ( ``CONNECTOR_STUB_PX`` ) の水平スタブを持ち、上下端入線でも入口直前が水平で
終端すること、折れ位置 (下折れ=出直後、上折れ=後続直前) と行間ギャップ通過が規則どおりであり、
同一行連続ケースで依存の向きが視覚的に正しく読めること、経路が中間アイテムのバウンディング
ボックスと交差しないことを単体テストで確認すること。
<<<
RELATIONS:
- TYPE: Parent
  VALUE: DEP-L1-003

[REQUIREMENT]
UID: DEP-L2-003
TYPE: Constraint
PRIORITY: Should
LAYER: L2_Component
TITLE: 担当者名表示と左端入線の非干渉
STATEMENT: >>>
担当者名をアイテムの左に右詰めで表示するとき (ITEM-L2-004)、依存線ルーティングエンジンおよび
ラベル描画は、担当者名の表示が依存線の左端入線 (DEP-L1-002 の middle_left アンカーへ入る
DEP-L1-003 の左辺入経路) の水平部分と干渉しないように配置すること。担当者名と左端入線の矢印 (→)
の水平部分が重なる場合は、担当者名の配置または入線経路を、両者が重ならないように調整すること。
<<<
RATIONALE: >>>
担当者名はアイテム左・右詰め (CR-004 Part 5、ITEM-L2-004) で表示され、依存線もアイテムの左辺
(middle_left) から入るため、両者が同じアイテム左側の空間を取り合う。非干渉レイアウトを規定して
担当者名と依存線の入口が視覚的に衝突しないようにする。DEP-L1-003 の左辺入規則を担当者名との
非干渉観点から補足する。CR-004 Part 5。
<<<
VERIFICATION: >>>
担当者名を表示したアイテムへ左辺 (middle_left) から依存線が入る配置を作ったとき、担当者名が
入線矢印の水平部分と重ならないことを描画計測で確認すること。
<<<
RELATIONS:
- TYPE: Parent
  VALUE: DEP-L1-003

[[/SECTION]]

[[SECTION]]
TITLE: 4. 折れ点数の制約 (Elbow-Count Constraint)

[REQUIREMENT]
UID: DEP-L2-002
TYPE: Constraint
PRIORITY: Must
LAYER: L2_Component
TITLE: 依存線の折れ曲がり点を前進 0〜3・重なり/後方/同一行連続 最大 4 に制限する
STATEMENT: >>>
依存線ルーティングエンジンは、1 本の依存線が持つ折れ曲がり点 (elbow、経路の方向が
変わる頂点) の数を、次のとおり制限すること。前進ケース (後続が先行より右かつ非隣接) は
0 以上 3 以下とする。重なり/後方/同一行連続 (隣接) ケースは 0 以上 4 以下とする。いずれの
ケースでも、上限内で折れ点数が最小となる経路を選択すること。CR-008 (承認 2026-07-21) Part 3
による上限緩和であり、CR-003 Part 3 / IM8 の「全ケース 0〜3」規則をここで上書きする。
<<<
RATIONALE: >>>
折れ点が多い線は視覚的ノイズになり依存の追跡を妨げる。前進ケースは L 字/Z 字程度の素直な
経路 (0〜3) に保つ。一方、CR-008 Part 1 (出口/入口の水平スタブ必須) ・Part 2 (視認方向の
正しさ) ・既存の非交差制約 (両バー・自バーを跨がない) を、重なり・後方・同一行連続の各ケースで
同時に満たすには幾何的に 4 折れが必要になり得るため、これらのケースの上限を 4 へ緩和する。
IM8 の上下端入線 (水平スタブ無しで 0〜3 に収めていた方式) は CR-008 の水平スタブ必須化・
正方向要求と両立しないため上書きする。user-order item34.3、CR-003 Part 3、CR-008 Part 3。
<<<
VERIFICATION: >>>
多様な始点/終点・障害物配置 (前進=後続が右かつ非隣接、および重なり・後方・同一行連続の各ケース)
で配線した各依存線の折れ点数を数え、前進ケースが 0〜3、重なり/後方/同一行連続ケースが 0〜4 の
範囲内であり、いずれも上限内で最小折れ点であることを単体テストで確認すること。
<<<
RELATIONS:
- TYPE: Parent
  VALUE: DEP-L1-003

[[/SECTION]]

[[SECTION]]
TITLE: 5. 矢じりの最小描画 (Minimal Arrowhead)

[REQUIREMENT]
UID: DEP-L1-004
TYPE: Constraint
PRIORITY: Should
LAYER: L1_System
TITLE: 依存線の矢じりを認識可能な最小サイズで描画する
STATEMENT: >>>
本システムは、依存線の終端に描く矢じり (arrowhead) を、向きを持つ矢印として認識できる
範囲で最小の大きさで描画し、線本体やアイテムの視認を妨げないこと。
<<<
RATIONALE: >>>
矢じりは依存の向きを伝えるために必要だが、大きすぎると一枚絵の情報密度を下げアイテムを
隠す。認識可能性を保った最小サイズにする (モックのフィードバック: 矢印は認識できるが
最小限であること)。
<<<
VERIFICATION: >>>
既定ズームで依存線を表示し、矢じりが向きを判別できる形状で描画されつつ、その外接寸法が
規定の上限 (例: 線幅の数倍程度) を超えないことを目視および描画寸法の計測で確認すること。
<<<
RELATIONS:
- TYPE: Parent
  VALUE: STK-L0-010

[[/SECTION]]

[[SECTION]]
TITLE: 6. 依存の種別とラグ/リード (Link Type & Lag/Lead)

[TEXT]
STATEMENT: >>>
本節は CR-001 (承認 2026-07-19) Part C で採用した依存の属性を規定する。依存線には、始点/
終点のどの端点同士を関係づけるかを表す種別 (linkType) と、端点間の時間オフセットを表す
符号付き lagDays を持たせる。いずれも MSPDI の PredecessorLink と往復し、MS Project 等の
他ツールでも解釈できる標準要素へ写す。データ形式の詳細は `40-data-format.sdoc` の DATA-JSON-008
(JSON) および DATA-MSPDI-004 (MSPDI 往復) を参照する。
<<<

[REQUIREMENT]
UID: DEP-L1-005
TYPE: Functional
PRIORITY: Should
LAYER: L1_System
TITLE: 依存に種別 (FS/SS/FF/SF) を持たせる
STATEMENT: >>>
本システムは、各依存に種別 linkType を持たせ、Finish-to-Start (FS)、Start-to-Start (SS)、
Finish-to-Finish (FF)、Start-to-Finish (SF) のいずれかを指定できること。既定は FS とする。
linkType は MSPDI の PredecessorLink / Type (FF=0, FS=1, SF=2, SS=3) と双方向に往復すること。
<<<
RATIONALE: >>>
依存は「先行終了後に後続開始 (FS)」だけでなく、同時開始 (SS)・同時終了 (FF)・先行開始後に
後続終了 (SF) といった端点関係を持つ。種別を保持することで MS Project 等との相互運用で
依存の意味が失われない。モデルへの追加は低コストで価値が高い。CR-001 Part C。
<<<
VERIFICATION: >>>
FS/SS/FF/SF を設定した依存を MSPDI へ Export し、PredecessorLink / Type がそれぞれ 1/3/0/2 と
なること、および当該 MSPDI を Import して同じ linkType が復元されることを単体テストで
確認すること。未指定の依存は FS として扱われること。
<<<
RELATIONS:
- TYPE: Parent
  VALUE: STK-L0-010

[REQUIREMENT]
UID: DEP-L1-006
TYPE: Functional
PRIORITY: Should
LAYER: L1_System
TITLE: 依存に符号付きラグ/リード (lagDays) を持たせる
STATEMENT: >>>
本システムは、各依存に符号付きの lagDays を持たせ、正値をラグ (待ち時間・後続を遅らせる
日数)、負値をリード (前倒し・後続を先行完了前に重ねて始める日数)、0 または未指定をオフセット
なしとして表現できること。lagDays は MSPDI の PredecessorLink / LinkLag (+ LagFormat) と往復
すること。ただし MSPDI のラグは稼働カレンダー基準で単位が可変であるのに対し、gr-scheduler は
カレンダーを持たないため lagDays を暦日として近似し、往復で端数がずれ得ることを許容する。
<<<
RATIONALE: >>>
依存には端点関係 (linkType) に加えて時間オフセットがある。例として FS+10d は先行終了の
10 日後に後続開始 (部品調達待ち・養生・承認待ち)、FS-5d は先行終了の 5 日前に後続開始
(ファストトラッキング) を表す。符号付き 1 フィールドで正=ラグ/負=リードを表し、MSPDI と
往復する。カレンダー非保持による暦日近似は形式差として明示する。CR-001 Part C。
<<<
VERIFICATION: >>>
lagDays に正値・負値・0 を設定した依存を MSPDI へ Export し、LinkLag と LagFormat (暦日近似) が
符号込みで出力されること、当該 MSPDI を Import して同符号の lagDays が復元されること、暦日近似
による許容誤差を単体テストで確認すること。
<<<
RELATIONS:
- TYPE: Parent
  VALUE: STK-L0-010

[[/SECTION]]
