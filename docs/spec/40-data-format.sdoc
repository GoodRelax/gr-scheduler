[DOCUMENT]
TITLE: gr-scheduler 設計 - データ形式契約 (Data Format)

[GRAMMAR]
IMPORT_FROM_FILE: gr-scheduler-grammar.sgra

[TEXT]
STATEMENT: >>>
本書は gr-scheduler の **データ形式契約** である。 `30-architecture.sdoc` で定義した
コアデータモデル ( **ScheduleDocument** ) を、 3 つの外部形式へ直列化する契約を定める。
1. JSON (主データ形式・ AI 向け・ item43 / IO-L1-001)、 2. MSPDI XML (MS Project 相互運用・
item42 / IO-L1-002)、 3. SVG (画面出力・ item44 / IO-L1-003)。各 [DATAFIELD] は
`Satisfies` 関係で要求 UID をトレースする。外部入力の検証・サニタイズは IO-L1-006 で
定義済みであり、本書では再定義せず参照するに留める。

コアモデル語彙 ( 30-architecture と共通 ) : ScheduleDocument = projectId, schemaVersion, title,
epochDate, viewState, sections[], rows[], items[], declaredCategories[], classificationNodeStates[],
dependencies[], annotations[] ( すべて flat 構造 )。透かし・カーソル・ロケール等の表示状態は
viewState 配下 ( viewState.watermark ほか ) に持ち、旧 meta / palette / i18n トップレベルオブジェクトは
持たない。 projectId は UUID (v4) の一意プロジェクト識別子であり、生成は adapter の id seam
( ``src/adapters/id/id-generator.ts`` = crypto.randomUUID ) が担い、 section / item は 8 文字
[A-Za-z0-9] の短一意 id を持つ。 id を欠く旧 JSON は Import 時に codec が決定的に補完する
( ``src/domain/usecase/id-migration.ts`` )。

本節の表は人間可読な要約であり、機械可読な単一真実源 ( SSOT ) は
``docs/api/gr-scheduler.schema.json`` ( JSON Schema draft 2020-12 ) である。当該ファイルは
``json-codec.ts`` が直列化・受理する形式を厳密に記述し、 ``src/domain/usecase/document-schema.ts``
が唯一の取込点として複製なしにアプリへ供給する ( vite build で単一 HTML にインライン )。
<<<

[[SECTION]]
TITLE: 1. JSON スキーマ (主データ形式)

[TEXT]
STATEMENT: >>>
JSON は内部モデルの正準表現であり、 Export した JSON を再 Import しても意味が保持される
(往復整合、 IO-L1-001)。永続データは flat 構造であり、 property キーは英語固定・値は単純文字列/
数値/真偽で持つ。多言語の UI ラベル ( 表示用の en/ja マップ ) は永続ドキュメントのフィールドでは
なく実行時の UI 関心事であり、 ``src/domain/usecase/i18n.ts`` が扱う ( 保存対象外・ ADR-008 )。
永続するのは表示ロケール選択の viewState.activeLocale のみである。トップレベルフィールドを次に示す。

.. list-table::
   :header-rows: 1
   :widths: 20 18 62

   * - フィールド
     - 型
     - 意味
   * - projectId
     - string
     - プロジェクト一意識別子 ( UUID v4 )。 DATA-JSON-014。
   * - schemaVersion
     - integer
     - スキーマ版 ( 0 以上の整数、 SSOT スキーマ準拠 )。 Import 時の互換判定に用いる。
   * - title
     - string
     - 日程表名 ( ヘッダー左上のスケジュール名 )。
   * - epochDate
     - string
     - 時間軸原点の ISO 8601 カレンダー日付。
   * - viewState
     - object
     - zoomX, zoomY, scrollX, scrollY, fontScale, leftPaneWidth,
       planActualDisplay (予実の可視フィルタ), planActualStyle ('overlap'|'separate',
       予実の描画スタイル・既定 overlap), dualCursor, watermark, activeLocale ほか。表示状態。
   * - sections
     - object[]
     - 大分類。 id, name(文字列), order, collapsed, rowIds[]。
   * - rows
     - object[]
     - 帯 (ribbon)。 id, sectionId, classificationLabel(文字列・必須),
       subClassificationLabel, majorLabel, middleLabel, minorLabel, order, depth(0|1|2)。
   * - items
     - object[]
     - マイルストーン/タスク。 1 帯に複数 (マルチバー)。詳細は下表。
   * - declaredCategories
     - object[]
     - 宣言済み分類。 major(必須), middle, minor(いずれも文字列)。
   * - classificationNodeStates
     - object[]
     - 分類ノードの表示状態。 major(必須), middle, minor, sortIndex, hidden。
   * - dependencies
     - object[]
     - 依存。 id, fromItemId, fromAnchor(0..8), toItemId, toAnchor, bends,
       linkType('FS'|'SS'|'FF'|'SF', 既定 FS), lagDays(符号付き整数・正=ラグ/負=リード)。
   * - annotations
     - object[]
     - 注釈。 id, annotationKind('callout-box'|'polyline'|'rounded-box'), strokeColor ほか
       (開いたオブジェクト)。
<<<

[TEXT]
STATEMENT: >>>
item ( アイテム ) の主なフィールド:

.. list-table::
   :header-rows: 1
   :widths: 22 78

   * - フィールド
     - 意味
   * - id, rowId
     - アイテム識別子と所属帯。
   * - itemKind
     - 'milestone' | 'task'。点イベントか期間か。
   * - startDate, endDate
     - ISO 日付。予定 (plan) スパンの意味に確定。 endDate はマイルストーンで null。
   * - actualStart, actualEnd
     - ISO 日付 ( 任意 )。同一アイテムの実績スパン ( CR-001 Part A )。 actualEnd は
       マイルストーンで null。両者が揃う/欠けるで実績表現を切り替える。
   * - progressRatio
     - number ( 任意 )。進行中バーの到達割合。イナズマ線 front 算出 (PLAN-L2-001) に用いる。
   * - targetDate
     - ISO 日付 ( 任意 )。期限 ( 目標終了日 ) マーカー ( ITEM-L1-011 )。バー端と独立。
   * - abbrev, fullName, description
     - 文字列。略称・正式名称・説明。
   * - majorCategory, middleCategory, minorCategory
     - 文字列。アイテムの大中小分類。
   * - assignee, status, remarks
     - 担当・ステータス・備考。
   * - milestoneShape, taskShape, iconShapeKind
     - 図形種別 ( マイルストーン図形 / タスク図形 / 図形種別キー )。
   * - strokeColor, fillColor, fillColorExplicit, lineWeight
     - 枠色・塗り色・明示塗り・線幅 ('thin'|'medium'|'thick')。 Overlap の予実塗りは fillColor
       1 色から彩度で導出し ( 予定=淡色 / 実績=濃色 )、非色の冗長符号は線幅 ( 予定=細 / 実績=太、
       破線は用いない ) で表す ( 描画上の派生であり fillColor は保存値・ CR-002 Part 1 )。
   * - labelPosition, labelOffset
     - 'auto'|'center'|'top'|'bottom'|'left'|'right'|'inner-left' と {dx, dy}。略称の表示位置。
       'inner-left' はバー内左揃え ( タスク既定 )、 'left' はバー外・左であり別概念として峻別する
       ( CR-003 Part 2 )。
   * - importance
     - number。 LOD (ズーム連動増減) の重要度。

実績は別アイテムに持たず同一アイテムの actualStart / actualEnd で保持し、旧 planActualKind /
planGroupId は廃止する。変更前予定 ( ベースライン ) は per-item フィールドではなく別ファイル
参照文書として扱う ( 下記 DATA-JSON-016、 CR-002 Part 3 )。予定/実績の可視フィルタは
viewState.planActualDisplay、描画スタイル (Overlap / Separate) は viewState.planActualStyle が
担う (下記 DATA-JSON-011)。
<<<

[TEXT]
STATEMENT: >>>
JSON 例 ( 1 セクション / 2 行 / マイルストーン 1 / 実績付きタスク 1 /
依存 1 / コメント 1 / 透かし / viewState ):

::

    {
      "projectId": "3f2504e0-4f89-41d3-9a0c-0305e82c3301",
      "schemaVersion": 1,
      "title": "Vehicle A Program",
      "epochDate": "2026-01-01",
      "viewState": {
        "zoomX": 1.0, "zoomY": 1.0, "scrollX": 0, "scrollY": 0,
        "fontScale": "M", "leftPaneWidth": 220,
        "planActualDisplay": "both", "planActualStyle": "overlap",
        "todayLineVisible": true, "activeLocale": "ja", "themePreference": "light",
        "dualCursor": {
          "primary": { "atDate": "2026-07-01", "mode": "vertical-line" },
          "secondary": { "atDate": "2026-09-01", "mode": "vertical-line" },
          "visible": true
        },
        "watermark": { "enabled": true, "userName": "pm-local", "timestamp": "2026-07-18T09:00:00Z" }
      },
      "sections": [
        { "id": "sec-1", "name": "Body", "order": 0, "collapsed": false, "rowIds": ["row-1", "row-2"] }
      ],
      "rows": [
        { "id": "row-1", "sectionId": "sec-1", "classificationLabel": "Design", "majorLabel": "Design", "middleLabel": "Styling", "minorLabel": "Exterior", "order": 0, "depth": 0 },
        { "id": "row-2", "sectionId": "sec-1", "classificationLabel": "Test", "majorLabel": "Test", "middleLabel": "Durability", "minorLabel": "Bench", "order": 1, "depth": 0 }
      ],
      "items": [
        {
          "id": "it-1", "rowId": "row-1", "itemKind": "milestone",
          "startDate": "2026-08-01", "endDate": null, "targetDate": "2026-08-01",
          "abbrev": "DR1", "fullName": "Design Review 1", "description": "",
          "majorCategory": "Design", "middleCategory": "Gate", "minorCategory": "",
          "assignee": "A. Sato", "status": "planned", "remarks": "",
          "milestoneShape": "diamond",
          "strokeColor": "#4E79A7", "fillColor": "#FFFFFF", "lineWeight": "medium",
          "labelPosition": "top", "labelOffset": { "dx": 0, "dy": -6 },
          "importance": 90
        },
        {
          "id": "it-2", "rowId": "row-2", "itemKind": "task",
          "startDate": "2026-08-10", "endDate": "2026-09-20",
          "actualStart": "2026-08-14", "actualEnd": null, "progressRatio": 0.4, "targetDate": "2026-09-30",
          "abbrev": "DUR", "fullName": "Durability Test", "description": "",
          "majorCategory": "Test", "middleCategory": "Durability", "minorCategory": "Bench",
          "assignee": "B. Tanaka", "status": "in-progress", "remarks": "",
          "iconShapeKind": "chevron", "taskShape": "chevron",
          "strokeColor": "#F28E2B", "fillColor": "#F6C89A", "lineWeight": "thick",
          "labelPosition": "inner-left", "labelOffset": { "dx": 0, "dy": 0 },
          "importance": 60
        }
      ],
      "dependencies": [
        { "id": "dep-1", "fromItemId": "it-1", "fromAnchor": 4, "toItemId": "it-2", "toAnchor": 3, "bends": 2, "linkType": "FS", "lagDays": 10 }
      ],
      "annotations": [
        { "id": "cm-1", "annotationKind": "callout-box", "strokeColor": "#B07AA1" }
      ]
    }
<<<

[DATAFIELD]
UID: DATA-JSON-001
FORMAT: JSON
PATH: $.schemaVersion
TITLE: スキーマ版
STATEMENT: >>>
JSON ドキュメントのスキーマ版。型・下限は SSOT スキーマ ( ``gr-scheduler.schema.json`` の
``schemaVersion`` = 0 以上の整数 ) が規定する ( semver 文字列ではない )。 Import 時に互換性を
判定し、現行版より古い場合は移行ステップ ( migration ) を段階適用して現行版へ引き上げてから
読み込む。移行不能な非互換版は拒否する。 Import はメモリ上の現ドキュメントを置換する (置換前に
未保存編集があればユーザーに確認する) 調停規則とし、これによりインポート途中のユーザー
編集との競合を避ける。往復整合の基準。
<<<
EXAMPLE: 1
RELATIONS:
- TYPE: Parent
  VALUE: IO-L1-001
  ROLE: Satisfies

[DATAFIELD]
UID: DATA-JSON-014
FORMAT: JSON
PATH: $.projectId
TITLE: プロジェクト識別子
STATEMENT: >>>
プロジェクト全体の一意識別子 ( UUID v4 )。作成時に adapter の id seam
( ``src/adapters/id/id-generator.ts`` の crypto.randomUUID ) が採番し、純粋ドメインは id を
データとして受け取るのみとする。 id を欠く旧 JSON の Import では codec が決定的 UUID を補完する
( ``src/domain/usecase/id-migration.ts`` )。 section / item も 8 文字 [A-Za-z0-9] の短一意 id を
持ち、既存 id と依存 / 分類参照は温存する。往復整合の対象。 UUID v4 の pattern 等の形状は
SSOT スキーマ ( ``gr-scheduler.schema.json`` の ``projectId`` ) が規定する。
<<<
RELATIONS:
- TYPE: Parent
  VALUE: IO-L1-001
  ROLE: Satisfies

[DATAFIELD]
UID: DATA-JSON-002
FORMAT: JSON
PATH: $.title
TITLE: メタ情報
STATEMENT: >>>
日程表のメタ情報はトップレベルの flat フィールドとして持つ。 title ( 日程表名・ヘッダー左上の
スケジュール名、 CANVAS-L1-004 ) と epochDate ( 時間軸原点の ISO 8601 カレンダー日付 ) がこれに
当たる。 schemaVersion ( DATA-JSON-001 ) と projectId ( DATA-JSON-014 ) も同じくトップレベルの
flat フィールドである。旧 meta オブジェクト ( title/locale/createdAt/author ) は持たず、ロケール
選択は viewState.activeLocale ( DATA-JSON-011 ) が担う。型は SSOT スキーマ
( ``gr-scheduler.schema.json`` の ``title`` / ``epochDate`` ) が規定する。
<<<
EXAMPLE: "title": "Vehicle A Program", "epochDate": "2026-01-01"
RELATIONS:
- TYPE: Parent
  VALUE: IO-L1-001
  ROLE: Satisfies
- TYPE: Parent
  VALUE: CANVAS-L1-004
  ROLE: Satisfies

[DATAFIELD]
UID: DATA-JSON-003
FORMAT: JSON
PATH: $.sections[]
TITLE: セクション配列
STATEMENT: >>>
大分類。 id, name(文字列), order, collapsed, rowIds[]。順序入替・表示/非表示 (collapsed) と
束ねる行を表す。 name は flat 文字列で持つ ( i18n マップではない )。
<<<
EXAMPLE: { "id": "sec-1", "name": "Body", "order": 0, "collapsed": false, "rowIds": ["row-1", "row-2"] }
RELATIONS:
- TYPE: Parent
  VALUE: IO-L1-001
  ROLE: Satisfies
- TYPE: Parent
  VALUE: SECT-L1-002
  ROLE: Satisfies

[DATAFIELD]
UID: DATA-JSON-004
FORMAT: JSON
PATH: $.rows[]
TITLE: 行 (帯) 配列
STATEMENT: >>>
帯 (ribbon)。 id, sectionId, classificationLabel(必須), subClassificationLabel, majorLabel,
middleLabel, minorLabel, order, depth(0|1|2)。 1 帯が複数アイテムを載せるマルチバー構造の受け皿。
分類ラベルは flat 文字列で持ち ( classification{major,middle,minor} のネスト/i18n マップではない )、
左ペインに固定表示される。
<<<
EXAMPLE: { "id": "row-1", "sectionId": "sec-1", "classificationLabel": "Design", "majorLabel": "Design", "middleLabel": "Styling", "minorLabel": "Exterior", "order": 0, "depth": 0 }
RELATIONS:
- TYPE: Parent
  VALUE: IO-L1-001
  ROLE: Satisfies
- TYPE: Parent
  VALUE: CANVAS-L1-002
  ROLE: Satisfies
- TYPE: Parent
  VALUE: SECT-L1-006
  ROLE: Satisfies

[DATAFIELD]
UID: DATA-JSON-005
FORMAT: JSON
PATH: $.items[]
TITLE: アイテム配列
STATEMENT: >>>
マイルストーン/タスク。 itemKind, startDate, endDate(null=マイルストーン), abbrev/fullName/description
(文字列), majorCategory/middleCategory/minorCategory(文字列), assignee, status, remarks 等を持つ。
略称・名称・分類はいずれも flat 文字列であり ( i18n マップや category{} ネストではない )、プロパティ
多項目 (PROP-L1-002) を保持する。必須項目は id, rowId, itemKind, startDate, endDate, abbrev,
importance, fillColor, strokeColor である。
<<<
EXAMPLE: { "id": "it-1", "rowId": "row-1", "itemKind": "milestone", "startDate": "2026-08-01", "endDate": null, "abbrev": "DR1", "importance": 90, "fillColor": "#FFFFFF", "strokeColor": "#4E79A7" }
RELATIONS:
- TYPE: Parent
  VALUE: IO-L1-001
  ROLE: Satisfies
- TYPE: Parent
  VALUE: ITEM-L1-001
  ROLE: Satisfies
- TYPE: Parent
  VALUE: PROP-L1-002
  ROLE: Satisfies

[DATAFIELD]
UID: DATA-JSON-006
FORMAT: JSON
PATH: $.items[]
TITLE: 実績スパン・進捗率 (予実を同一アイテムで保持)
STATEMENT: >>>
予実を同一アイテムで持つ (CR-001 Part A)。 startDate / endDate が予定スパン、 actualStart /
actualEnd ( 任意、 マイルストーンは actualEnd = null ) が実績スパン、 progressRatio ( 任意 ) が
進行中バーの到達割合を表す。イナズマ線 front はこれらから PLAN-L2-001 の統一規則で算出する
( マイルストーンは点に退化し、実績あれば actualStart・無ければ startDate を用い補間しない・
CR-002 Part 2 )。旧 planActualKind / planGroupId は廃止し、データに残さない。変更前予定
( ベースライン ) は本アイテムのフィールドではなく別ファイル参照文書で扱う ( DATA-JSON-016、
CR-002 Part 3 )。各フィールドの型・形状は SSOT スキーマ ( ``gr-scheduler.schema.json`` の
``$defs/item`` ) が規定する。
<<<
RELATIONS:
- TYPE: Parent
  VALUE: IO-L1-001
  ROLE: Satisfies
- TYPE: Parent
  VALUE: PLAN-L1-001
  ROLE: Satisfies

[DATAFIELD]
UID: DATA-JSON-007
FORMAT: JSON
PATH: $.items[]
TITLE: アイコン・スタイル・略称位置
STATEMENT: >>>
milestoneShape / taskShape / iconShapeKind ( 図形種別 )、
fillColor / fillColorExplicit / strokeColor / lineWeight ( 塗り色・明示塗り・枠色・線幅 )、
labelPosition / labelOffset ( 略称の表示位置 ) を表す。
labelPosition の値域には 'inner-left' ( バー内左揃え・タスク既定 ) を含め、バー外の 'left' とは
別概念として峻別する ( CR-003 Part 2。 'inner-left' は現行 SSOT スキーマ
``gr-scheduler.schema.json`` の ``$defs/item.labelPosition`` enum に反映済み )。 Overlap の予実塗りは fillColor 1 色からの彩度
導出 ( 予定=淡 / 実績=濃 ) と線幅 ( 予定=細 / 実績=太、 破線不使用 ) で表す描画上の派生であり、
fillColor 自体は保存値のまま ( CR-002 Part 1 )。各フィールドの型・形状は SSOT スキーマ
( ``gr-scheduler.schema.json`` の ``$defs/item`` ) が規定する。
<<<
RELATIONS:
- TYPE: Parent
  VALUE: IO-L1-001
  ROLE: Satisfies
- TYPE: Parent
  VALUE: ITEM-L1-006
  ROLE: Satisfies
- TYPE: Parent
  VALUE: ITEM-L1-009
  ROLE: Satisfies

[DATAFIELD]
UID: DATA-JSON-008
FORMAT: JSON
PATH: $.dependencies[]
TITLE: 依存配列
STATEMENT: >>>
依存。 fromItemId / fromAnchor / toItemId / toAnchor ( 9 点アンカー )、 bends ( ルータ算出の
折れ点数 )、 linkType ( 端点関係 )、 lagDays ( 符号付き時間オフセット、 正=ラグ/負=リード/
0・未指定=なし ) を持つ ( CR-001 Part C )。 linkType / lagDays は MSPDI PredecessorLink の
Type / LinkLag と往復する ( DATA-MSPDI-004 )。 CR-003 Part 3 では配線を自動のみとし、始点=先行の
右端・終点=後続の左端に固定した決定的直交配線へ specialize する ( 9 点アンカーの座標定義自体は
DEP-L1-002 に保持 )。各フィールドの型・値域・既定 ( linkType 既定 FS ) は SSOT スキーマ
( ``gr-scheduler.schema.json`` の ``$defs/dependency`` ) が規定する。
<<<
RELATIONS:
- TYPE: Parent
  VALUE: IO-L1-001
  ROLE: Satisfies
- TYPE: Parent
  VALUE: DEP-L1-002
  ROLE: Satisfies
- TYPE: Parent
  VALUE: DEP-L1-005
  ROLE: Satisfies
- TYPE: Parent
  VALUE: DEP-L1-006
  ROLE: Satisfies

[DATAFIELD]
UID: DATA-JSON-009
FORMAT: JSON
PATH: $.annotations[]
TITLE: 注釈配列 (コメント / 丸角囲み)
STATEMENT: >>>
注釈は id と annotationKind('callout-box'|'polyline'|'rounded-box') を必須とする flat な開いた
オブジェクトである。 callout-box / polyline は引出し四角/折れ線コメント、 rounded-box は丸角囲みを
表す。 variant 固有フィールドはモデル側の判別共用体が担保し、 codec は共通フィールド ( id,
annotationKind, strokeColor ) のみ検証する ( additionalProperties true )。旧 comment{} /
roundedBox{} ラッパは持たない。
<<<
EXAMPLE: { "id": "cm-1", "annotationKind": "callout-box", "strokeColor": "#B07AA1" }
RELATIONS:
- TYPE: Parent
  VALUE: IO-L1-001
  ROLE: Satisfies
- TYPE: Parent
  VALUE: CURS-L1-006
  ROLE: Satisfies
- TYPE: Parent
  VALUE: CURS-L1-007
  ROLE: Satisfies

[DATAFIELD]
UID: DATA-JSON-010
FORMAT: JSON
PATH: $.viewState.watermark
TITLE: 透かし
STATEMENT: >>>
enabled, userName, timestamp ( hideHash 任意 )。ローカル入力ユーザー名と日時の透かし。トップレベル
ではなく viewState 配下に持つ ( DATA-JSON-011 )。 SVG 出力にも有効時に含める。
<<<
EXAMPLE: { "enabled": true, "userName": "pm-local", "timestamp": "2026-07-18T09:00:00Z" }
RELATIONS:
- TYPE: Parent
  VALUE: IO-L1-001
  ROLE: Satisfies
- TYPE: Parent
  VALUE: TOOL-L1-007
  ROLE: Satisfies

[DATAFIELD]
UID: DATA-JSON-011
FORMAT: JSON
PATH: $.viewState
TITLE: 表示状態
STATEMENT: >>>
zoomX/zoomY (異方性), scrollX/scrollY, fontScale('S'|'M'|'L'), leftPaneWidth,
planActualDisplay('plan-only'|'actual-only'|'both'|'none' = 予実の可視フィルタ),
planActualStyle('overlap'|'separate', 既定 overlap = 予実の描画スタイル・CR-001 Part A),
todayLineVisible, gridDateLinesVisible, gridCategoryLinesVisible, progressLineVisible,
progressLineColor, dualCursor{primary, secondary, visible} ( 各 cursorState = atDate +
mode('vertical-line'|'crosshair') ), cursorGuideMode, watermark, activeLocale('en'|'ja'),
themePreference。ズーム・スクロール・カーソル・フォント段階に加え予実の可視/スタイル・透かし・
ロケール・テーマを永続化し、再 Import で見え方を復元する。旧 timeGranularity / cursors{today,dual}
は持たず、本日線は todayLineVisible、二重カーソルは dualCursor が担う。 planActualDisplay ( 何を
見せるか ) と planActualStyle ( どう重ねる/分けるか ) は独立とする。

実装フェーズ橋渡し (CR-006 Part 5): progressLineVisible の既定値を「表示」から「非表示」へ変更
する。すなわち未指定時のイナズマ線描画を既定オフとする (PLAN-L1-003)。本フェーズでは
docs/api/gr-scheduler.schema.json は改訂せず (schema-conformance テストの赤化回避)、既定値変更は
実装セッションで schema / ドメインモデルへ反映する。
<<<
EXAMPLE: { "zoomX": 1.0, "zoomY": 1.0, "scrollX": 0, "scrollY": 0, "fontScale": "M", "planActualDisplay": "both", "planActualStyle": "overlap", "todayLineVisible": true, "activeLocale": "ja", "dualCursor": { "primary": { "atDate": "2026-07-01", "mode": "vertical-line" }, "secondary": { "atDate": "2026-09-01", "mode": "vertical-line" }, "visible": true } }
RELATIONS:
- TYPE: Parent
  VALUE: IO-L1-001
  ROLE: Satisfies
- TYPE: Parent
  VALUE: ZOOM-L1-003
  ROLE: Satisfies
- TYPE: Parent
  VALUE: CURS-L1-002
  ROLE: Satisfies
- TYPE: Parent
  VALUE: PLAN-L1-002
  ROLE: Satisfies
- TYPE: Parent
  VALUE: PLAN-L1-005
  ROLE: Satisfies

[DATAFIELD]
UID: DATA-JSON-012
FORMAT: JSON
PATH: $.viewState.activeLocale
TITLE: パレットと i18n 設定
STATEMENT: >>>
色弱者配慮 (CUD) のカラーパレットと UI 表示言語は、永続ドキュメントのトップレベルフィールドでは
ない。パレット候補色は実行時 UI の関心事であり、多言語 UI ラベルは ``src/domain/usecase/i18n.ts``
が en/ja マップとして扱う ( 保存対象外・ ADR-008 )。永続するのは表示ロケール選択の
viewState.activeLocale('en'|'ja') とテーマ選択の viewState.themePreference のみである
( DATA-JSON-011 )。 property キーは英語固定。旧 palette / i18n{locales,activeLocale} トップレベル
オブジェクトは持たない。
<<<
EXAMPLE: { "viewState": { "activeLocale": "ja", "themePreference": "light" } }
RELATIONS:
- TYPE: Parent
  VALUE: IO-L1-001
  ROLE: Satisfies
- TYPE: Parent
  VALUE: PROP-L1-005
  ROLE: Satisfies
- TYPE: Parent
  VALUE: PROP-L1-003
  ROLE: Satisfies

[DATAFIELD]
UID: DATA-JSON-015
FORMAT: JSON
PATH: $.items[].targetDate
TITLE: 期限 (目標終了日) マーカー
STATEMENT: >>>
アイテムの任意の期限 ( 目標終了日 )。バー端 ( startDate / endDate ) と独立した「ここまで」の
目標マーカーを当該日付に描く ( ITEM-L1-011、 CR-001 Part C )。 MSPDI の Deadline と往復する
( DATA-MSPDI-009 )。スケジューラを持たない gr-scheduler では制約 ( Constraint ) ではなく目標線
として扱う。往復整合の対象。型・形状は SSOT スキーマ ( ``gr-scheduler.schema.json`` の
``$defs/item.targetDate`` ) が規定する。
<<<
RELATIONS:
- TYPE: Parent
  VALUE: IO-L1-001
  ROLE: Satisfies
- TYPE: Parent
  VALUE: ITEM-L1-011
  ROLE: Satisfies

[DATAFIELD]
UID: DATA-JSON-016
FORMAT: JSON
PATH: (baseline reference document, id-matched)
TITLE: ベースライン参照文書 (別ファイル・読取専用)
STATEMENT: >>>
変更前予定 ( ベースライン ) は、現行ドキュメントの per-item フィールドではなく、独立した JSON
文書 ( 過去予定スナップショット ) として読み込む ( CR-002 Part 3 が CR-001 Part A の
previousPlan 据え置きを supersede し、 item.previousPlan フィールドを廃止する )。この参照文書は
gr-scheduler JSON 形式であり、 Load 時のオプションで「ベースライン扱い」を明示指定して読取専用で
取り込む ( 通常の編集対象としての Load とは区別する )。参照形式は JSON のみで MSPDI XML は不可。
現行アイテムとの対応付けは id をキーに突合し、対応アイテムの予定日のみを用いて対象行と同じ高さの
薄いグレー・編集不可アンダーレイとして描く ( 参照文書内の実績は無視・オフセットしない )。
ベースライン層の表示/非表示はヘッダーの専用トグル ( Visible / Invisible ) で切り替え、予実の可視
フィルタ ( planActualDisplay ) とは独立とする ( ヘッダー配置は CR-003 Part 1 に従う )。参照文書
自体の型・形状は本書の JSON スキーマ ( SSOT、 ``gr-scheduler.schema.json`` ) に従う。
<<<
RELATIONS:
- TYPE: Parent
  VALUE: IO-L1-001
  ROLE: Satisfies
- TYPE: Parent
  VALUE: PLAN-L1-004
  ROLE: Satisfies

[[/SECTION]]

[[SECTION]]
TITLE: 2. MSPDI XML マッピング

[TEXT]
STATEMENT: >>>
本節のマッピングは MS Project の公式 MSPDI ( Microsoft Project Data Interchange ) 仕様に
準拠する。規範的出典 ( normative reference ) を次に示す。 MSPDI は ISO 等の標準化団体規格では
なく Microsoft のベンダー公開スキーマだが、後継 Project デスクトップ版も同形式で入出力するため
事実上の共通契約である。取得した参照コピーは ``docs/spec/vendor/mspdi/`` に置き ( ライセンス上
git 管理外・ README のみ追跡、再取得手順は当該 README を参照 )、実装時のスキーマ検証・要素確認に
用いる。

- XSD schema (mspdi_pj12.xsd, Project 2007): https://schemas.microsoft.com/project/2007/mspdi_pj12.xsd
- Element reference (Microsoft Learn): https://learn.microsoft.com/en-us/office-project/xml-data-interchange/introduction-to-project-xml-data
- Project elements and XML structure: https://learn.microsoft.com/en-us/office-project/xml-data-interchange/project-elements-and-xml-structure
- Docs source repo (CC-BY-4.0): https://github.com/MicrosoftDocs/office-developer-msproject-xml-docs
<<<

[TEXT]
STATEMENT: >>>
MS Project の交換形式 MSPDI XML と gr-scheduler モデルの対応を定める (IO-L1-002)。
MSPDI は「 1 タスク = 1 行 = 1 バー」を前提とし、 gr-scheduler の表現の多くに直接対応が
無い。対応が無い概念は名前空間付き JSON サイドカーで往復保持し、それが不可能なものは
ロッシー (欠落) として明示する。

.. list-table::
   :header-rows: 1
   :widths: 30 30 40

   * - gr-scheduler モデル
     - MSPDI 要素
     - 備考
   * - title
     - Project / Name, Project / Title
     - プロジェクト名 ( トップレベル flat フィールド )。 Export は同じ値を Name と Title の双方へ
       出力する ( XSD の順序どおり Name が先 )。 Import は Title を正とし、無い/空のときのみ
       Name へフォールバックする ( DATA-MSPDI-001 )。
   * - ( 作成日: 非永続 )
     - Project / CreationDate
     - flat スキーマは作成日フィールドを持たない。 CreationDate は Export 時に生成し、 Import では
       読み飛ばす。
   * - item (itemKind=task)
     - Tasks / Task
     - id -> Task / UID。
   * - item.fullName
     - Task / Name
     - 正式名称 ( flat 文字列 ) を採用。
   * - item.startDate
     - Task / Start
     - ISO 日時。
   * - item.endDate
     - Task / Finish
     - タスクの終了。マイルストーンは Start=Finish。
   * - item (itemKind=milestone)
     - Task / Milestone = 1
     - end=null を Milestone フラグで表す。
   * - item.actualStart / actualEnd
     - Task / ActualStart, ActualFinish
     - 実績スパンを標準要素で往復 (B-4)。実績なしは要素を出さない。
   * - item.progressRatio
     - Task / PercentComplete
     - 進捗率 0..1 を 0..100 (整数%) へ往復 (B-3)。
   * - ベースライン参照文書 (別ファイル・ id 突合)
     - Task / BaselineStart, BaselineFinish
     - 読み込んだベースライン参照文書 (DATA-JSON-016) を id 突合し best-effort で合成/往復
       (B-4 の clean 往復から格下げ・ CR-002 Part 3)。 Baseline Number は 0。 previousPlan
       フィールドは廃止。
   * - item.targetDate (期限)
     - Task / Deadline
     - 目標終了日を Deadline で往復 (Part C)。 Constraint ( ルール ) は見送り。
   * - item.description
     - Task / Notes
     - タスク説明を Notes へ (B-6)。サイドカー JSON とは格納位置/接頭辞で分離する。
   * - dependency
     - Task / PredecessorLink
     - fromItemId -> PredecessorUID。 linkType -> Type (FF=0/FS=1/SF=2/SS=3)、 lagDays ->
       LinkLag(+LagFormat, 暦日近似)。 9 点アンカー/bends はサイドカーへ (Part C, B-4)。
   * - section / row 階層
     - Task / OutlineLevel, Summary
     - セクション = 上位サマリタスク (Summary=1)、行 = 下位。 Import も OutlineLevel を読んで
       階層復元 (B-1)。分類名は Name へ。
   * - row.majorLabel / middleLabel / minorLabel
     - Task / OutlineNumber, Name
     - 大中小分類ラベル ( flat 文字列 ) は要約タスク階層 + 名前で近似。 minorLabel まで表せない分は
       サイドカーへ。
   * - assignee
     - Resources / Resource, Assignments / Assignment
     - 担当者を Resource として出力し Assignment で割当。 Import も Resource/Assignment を
       読んで assignee を復元 (B-2)。
   * - マルチバー ( SplitParts )
     - Task / Splits ( SplitPart )
     - Import 時に分割区間 SplitPart を GR の 1 行複数アイテム ( マルチバー ) へ写す (B-5)。
   * - 拡張属性 一括
     - Task / ExtendedAttribute, Task / Notes
     - 下記 サイドカー参照。
<<<

[TEXT]
STATEMENT: >>>
**MSPDI に対応概念が無い gr-scheduler 概念** ( 往復保持の方針 ):

.. list-table::
   :header-rows: 1
   :widths: 40 60

   * - 概念
     - 往復保持の方針
   * - マルチバー ( 1 行に複数アイテム )
     - サイドカー JSON の rowId でグルーピングを保持。 MSPDI 単体では別タスクに分解される。
   * - アイコン / 図形 / 絵文字
     - サイドカーへ icon をそのまま保持。 MSPDI には表現無し ( ロッシー )。
   * - 色 / 線幅 / 略称位置 ( style, labelPosition )
     - サイドカーへ保持。 MSPDI には表現無し。
   * - コメント / 丸角囲み ( annotations )
     - サイドカーへ保持。 MSPDI には表現無し。
   * - 透かし ( watermark )
     - サイドカーへ保持。 MSPDI には表現無し。
   * - ベースライン参照文書 ( 変更前予定 )
     - 別ファイルの参照文書 (DATA-JSON-016) を id 突合し、標準要素 Task / BaselineStart,
       BaselineFinish で best-effort 往復する ( 突合できない項は往復しない・ロッシー )。
       サイドカーは補助 ( 端数・整合の担保 ) に留める。 previousPlan フィールドは廃止。
   * - viewState ( ズーム / カーソル / フォント )
     - サイドカーへ保持。 MSPDI には表現無し。

サイドカーは、名前空間付き JSON を Project / Task の Notes フィールドへ格納するか、数値 FieldID
+ Alias を定義した ExtendedAttributes カスタムフィールドへ格納する ( MSPDI の FieldID は数値の
MS カスタムフィールド ID であり、文字列名は使えない )。 Import 時はサイドカーがあれば
優先して gr-scheduler 固有情報を復元し、無ければ MSPDI 標準要素のみから最小構成を生成する。
Import は IO-L1-006 に従い XXE を無効化して検証する ( 本書では再定義しない )。
<<<

[DATAFIELD]
UID: DATA-MSPDI-001
FORMAT: MSPDI_XML
PATH: Project
TITLE: プロジェクトルート
STATEMENT: >>>
MSPDI の Project 要素へ title を Project / Name と Project / Title の双方としてマッピングする。
Export は同一のプロジェクト名を Name と Title の両要素へ出力し、出力順は vendored な
``mspdi_pj12.xsd`` が定める xsd:sequence ( UID? → Name? → Title? → … → CreationDate? ) に
従い Name を先、 Title を後とする。 Import は Title を正 ( authoritative ) とし、 Title が
無い/空文字のときに限り Name をフォールバックとして採り、いずれも無い/空のときは既定の
プレースホルダ ( ``Imported project`` ) を用いる。この Name / Title の探索は Project の
スカラ領域 ( 最初の ``<Tasks>`` より前 ) に限定し、タスク自身の Name をプロジェクト名と
取り違えないこと。作成日は flat スキーマに無く、 CreationDate は Export 時に生成し Import では
読み飛ばす。 gr-scheduler 固有の往復情報は Notes フィールドまたは数値 FieldID の
ExtendedAttributes カスタムフィールドへサイドカーとして格納する ( DATA-MSPDI-006 )。

Title のみを出力する旧規定は本規定が supersede する。 MS Project がプロジェクト名として提示するのは
Name であり、 Title のみの出力では相手側でプロジェクト名が空に見えるため、双方へ出力する。
Title を Import の正とするのは、 Title を持つ既存ファイルに対して従来と同一の結果を返し、
実質的な後方互換を保つためである。 CR-016。
<<<
EXAMPLE: <Project><Name>Vehicle A Program</Name><Title>Vehicle A Program</Title><CreationDate>2026-07-18T00:00:00</CreationDate></Project>
RELATIONS:
- TYPE: Parent
  VALUE: IO-L1-002
  ROLE: Satisfies

[DATAFIELD]
UID: DATA-MSPDI-002
FORMAT: MSPDI_XML
PATH: Project/Tasks/Task
TITLE: タスク (UID / Name)
STATEMENT: >>>
item を Task へ写す。 item.id -> Task / UID、 item.fullName ( flat 文字列 ) -> Task / Name。
<<<
EXAMPLE: <Task><UID>2</UID><Name>Durability Test</Name></Task>
RELATIONS:
- TYPE: Parent
  VALUE: IO-L1-002
  ROLE: Satisfies
- TYPE: Parent
  VALUE: ITEM-L1-001
  ROLE: Satisfies

[DATAFIELD]
UID: DATA-MSPDI-003
FORMAT: MSPDI_XML
PATH: Project/Tasks/Task/Start
TITLE: 予定 / 実績 / ベースライン / マイルストーン
STATEMENT: >>>
予実を MSPDI 標準要素へ往復する (CR-001 Part A / B-4)。 item.startDate -> Task / Start、
item.endDate -> Task / Finish ( 予定スパン )。 item.actualStart -> Task / ActualStart、
item.actualEnd -> Task / ActualFinish ( 実績なしは要素を出さない )。変更前予定 ( ベースライン ) は
per-item フィールドではなく別ファイル参照文書 ( DATA-JSON-016 ) として持つため、 Task /
BaselineStart, BaselineFinish ( Baseline Number = 0 ) へは、読み込んだ参照文書を id 突合して
best-effort で合成/往復する ( CR-002 Part 3 が CR-001 B-4 の previousPlan ↔ Baseline の clean
往復を格下げ。突合できない項は往復しない・ロッシー )。 itemKind=milestone ( endDate=null ) は
Task / Milestone = 1 かつ Start = Finish で表し、実績も actualEnd=null 時は ActualStart のみ。
planActualKind / planGroupId は廃止のため写さない。
<<<
EXAMPLE: <Start>2026-08-10T08:00:00</Start><Finish>2026-09-20T17:00:00</Finish><ActualStart>2026-08-14T08:00:00</ActualStart><Milestone>0</Milestone>
RELATIONS:
- TYPE: Parent
  VALUE: IO-L1-002
  ROLE: Satisfies
- TYPE: Parent
  VALUE: PLAN-L1-001
  ROLE: Satisfies
- TYPE: Parent
  VALUE: PLAN-L1-004
  ROLE: Satisfies

[DATAFIELD]
UID: DATA-MSPDI-004
FORMAT: MSPDI_XML
PATH: Project/Tasks/Task/PredecessorLink
TITLE: 依存 (先行タスクリンク・種別・ラグ)
STATEMENT: >>>
dependency を PredecessorLink へ写す。 fromItemId -> PredecessorUID。 dependency.linkType ->
Type ( FF=0, FS=1, SF=2, SS=3。 既定 FS=1 )。 dependency.lagDays -> LinkLag ( + LagFormat )。
LinkLag は経過時間を 1/10 分単位で符号化する。 gr-scheduler はカレンダーを持たず lagDays を
暦日 ( elapsed days ) として近似するため、暦日 1 日 = 24h x 60 x 10 = 14400、 lagDays 10 は
LinkLag 144000 ( LagFormat=8 は暦日 / elapsed days ) となる。
MSPDI のラグは稼働カレンダー基準・単位可変だが gr-scheduler はカレンダー非保持のため lagDays を
暦日として近似し、往復で端数がずれ得る ( 形式差 )。 LagFormat は暦日 ( elapsed days ) を示す
8 を用い、負値はリード ( 前倒し ) を表す。 9 点アンカー ( fromAnchor / toAnchor ) と bends は MSPDI に無く
サイドカーへ保持する ( CR-001 Part C )。
<<<
EXAMPLE: <PredecessorLink><PredecessorUID>1</PredecessorUID><Type>1</Type><LinkLag>144000</LinkLag><LagFormat>8</LagFormat></PredecessorLink>
RELATIONS:
- TYPE: Parent
  VALUE: IO-L1-002
  ROLE: Satisfies
- TYPE: Parent
  VALUE: DEP-L1-001
  ROLE: Satisfies
- TYPE: Parent
  VALUE: DEP-L1-005
  ROLE: Satisfies
- TYPE: Parent
  VALUE: DEP-L1-006
  ROLE: Satisfies

[DATAFIELD]
UID: DATA-MSPDI-005
FORMAT: MSPDI_XML
PATH: Project/Tasks/Task/OutlineLevel
TITLE: セクション / 行 階層
STATEMENT: >>>
section / row の階層を OutlineLevel + サマリタスクで表す。セクションは上位サマリタスク、
行は下位。 rowId でのマルチバーグルーピングと minor 分類はサイドカーで補完する。
<<<
EXAMPLE: <OutlineLevel>2</OutlineLevel><OutlineNumber>1.1</OutlineNumber>
RELATIONS:
- TYPE: Parent
  VALUE: IO-L1-002
  ROLE: Satisfies
- TYPE: Parent
  VALUE: SECT-L1-002
  ROLE: Satisfies

[DATAFIELD]
UID: DATA-MSPDI-006
FORMAT: MSPDI_XML
PATH: Project/Task/Notes
TITLE: 名前空間付き JSON サイドカー (往復保持)
STATEMENT: >>>
MSPDI に対応概念が無い gr-scheduler 情報 ( マルチバー / アイコン / 色 / 略称位置 / コメント /
丸角囲み / 透かし / viewState ) を名前空間付き JSON として保持する。
MSPDI の FieldID は数値の MS カスタムフィールド ID であり文字列名を持てないため、サイドカーは
Task ( または Project ) の Notes フィールドへ格納するか、数値 FieldID + Alias を定義した
ExtendedAttributes カスタムフィールドへ格納する。存在しない場合は MSPDI 標準要素のみから最小構成を
生成する ( ロッシー )。
<<<
EXAMPLE: <Notes>grsch-sidecar:{ "rowGroups": {}, "icons": {}, "watermark": {} }</Notes>
RELATIONS:
- TYPE: Parent
  VALUE: IO-L1-002
  ROLE: Satisfies

[DATAFIELD]
UID: DATA-MSPDI-007
FORMAT: MSPDI_XML
PATH: Project/Resources/Resource
TITLE: 担当・進捗 (Resource / PercentComplete)
STATEMENT: >>>
実装漏れ B-2 / B-3 の解消。 item.assignee を Resources / Resource として出力し
Assignments / Assignment ( TaskUID + ResourceUID ) で当該タスクへ割り当てる。 Import も
Resource / Assignment を読んで assignee を復元する。 item.progressRatio ( 0..1 ) は
Task / PercentComplete ( 0..100 の整数% ) へ往復する。いずれも MSPDI 標準要素であり他ツールで
可視となる ( CR-001 Part B / Part C )。
<<<
EXAMPLE: <Resource><UID>1</UID><Name>B. Tanaka</Name></Resource>  ... <Task><PercentComplete>40</PercentComplete></Task>
RELATIONS:
- TYPE: Parent
  VALUE: IO-L1-002
  ROLE: Satisfies
- TYPE: Parent
  VALUE: PROP-L1-002
  ROLE: Satisfies
- TYPE: Parent
  VALUE: PLAN-L1-003
  ROLE: Satisfies

[DATAFIELD]
UID: DATA-MSPDI-008
FORMAT: MSPDI_XML
PATH: Project/Tasks/Task/Splits
TITLE: 分割タスク・タスク説明 (SplitParts / Notes)
STATEMENT: >>>
実装漏れ B-5 / B-6 の解消。 Import 時、 Task / Splits の SplitPart ( 分割区間 ) を GR の
1 行複数アイテム ( マルチバー ) へ写し、連続バーに潰さない。 item.description は Task / Notes へ
格納する。サイドカー JSON ( DATA-MSPDI-006 ) も Notes を用いるため、接頭辞 ( 例 grsch-sidecar: )
と本文説明を分離して両立させる ( 説明本文が先、サイドカーは識別接頭辞付きで併記 )。
<<<
EXAMPLE: <Splits><SplitPart><Start>2026-08-10T08:00:00</Start><Finish>2026-08-20T17:00:00</Finish></SplitPart></Splits>
RELATIONS:
- TYPE: Parent
  VALUE: IO-L1-002
  ROLE: Satisfies
- TYPE: Parent
  VALUE: ITEM-L1-001
  ROLE: Satisfies

[DATAFIELD]
UID: DATA-MSPDI-009
FORMAT: MSPDI_XML
PATH: Project/Tasks/Task/Deadline
TITLE: 期限 (Deadline) と制約 (Constraint) の扱い
STATEMENT: >>>
item.targetDate ( 期限・目標終了日 ) を Task / Deadline へ往復する ( CR-001 Part C )。
Deadline はスケジューラを動かさない目標線であり、スケジューラを持たない gr-scheduler と整合
する。一方 Constraint ( ConstraintType / ConstraintDate = ルール ) は、適用先のスケジューラが
無いため取り込まず見送る ( 往復対象外・ロッシー )。 Import で Constraint のみを持つタスクは
targetDate を生成しない。
<<<
EXAMPLE: <Deadline>2026-09-30T17:00:00</Deadline>
RELATIONS:
- TYPE: Parent
  VALUE: IO-L1-002
  ROLE: Satisfies
- TYPE: Parent
  VALUE: ITEM-L1-011
  ROLE: Satisfies

[[/SECTION]]

[[SECTION]]
TITLE: 3. SVG 出力契約

[TEXT]
STATEMENT: >>>
画面の SVG 出力 (IO-L1-003) の契約を定める。出力は現在表示中の日程表を再現し、外部リソースに
依存せず単体で開ける自己完結 SVG とする。

.. list-table::
   :header-rows: 1
   :widths: 28 72

   * - 項目
     - 契約
   * - 内容
     - レイアウト済みの帯・アイテム ( 図形/略称 )・分類水平線・依存線 ( 最小矢頭 )・
       コメント/丸角囲み・本日線/カーソルを、画面と同一レンダラ (ARCH-C-022) で描く。
   * - 透かし
     - watermark.enabled が真のとき、斜めタイル配置の透かし層を含める (TOOL-L1-007)。
   * - 自己完結
     - 外部 CDN や外部画像参照を持たず、自己完結した SVG として出力する ( CR-004 Part 6a で
       外部画像インポートは撤回済み )。
   * - フォント / テキスト
     - 略称等のテキストは SVG text 要素で出力する。フォント差異による再現ずれを避けたい
       用途では、テキストをアウトライン化 (path) するオプションを設ける。
   * - 座標系
     - 画面空間固定要素 ( 丸角囲みの角丸み・依存矢頭・透かし ) は CSS px サイズで、日付/行
       空間要素は現在ズームのスケールで焼き込む (ADR-004)。
   * - サニタイズ
     - 出力する SVG には実行可能要素を含めず、略称等のテキストは出力時にエスケープする
       ( security-design C-02、本書では再定義しない )。
<<<

[DATAFIELD]
UID: DATA-SVG-001
FORMAT: SVG
PATH: svg
TITLE: 自己完結 SVG ルート
STATEMENT: >>>
現在表示中の日程表を再現する SVG ルート。 viewBox とサイズを持ち、外部参照なしで単体表示
できる。埋め込み画像は data URI とする。
<<<
EXAMPLE: <svg xmlns="http://www.w3.org/2000/svg" viewBox="0 0 1600 900"> ... </svg>
RELATIONS:
- TYPE: Parent
  VALUE: IO-L1-003
  ROLE: Satisfies

[DATAFIELD]
UID: DATA-SVG-002
FORMAT: SVG
PATH: svg/g[watermark]
TITLE: 透かし層
STATEMENT: >>>
watermark.enabled が真のとき出力する透かしグループ。ユーザー名 + 日時を斜め方向へ薄く
複数タイル配置する。無効時は出力しない。
<<<
EXAMPLE: <g id="watermark" opacity="0.12"> <text transform="rotate(-30)">pm-local 2026-07-18</text> </g>
RELATIONS:
- TYPE: Parent
  VALUE: IO-L1-003
  ROLE: Satisfies
- TYPE: Parent
  VALUE: TOOL-L1-007
  ROLE: Satisfies

[DATAFIELD]
UID: DATA-SVG-003
FORMAT: SVG
PATH: svg/text
TITLE: テキスト / フォント処理
STATEMENT: >>>
略称・分類名・ヘッダー等のテキストは text 要素で出力する。再現性重視の用途では path への
アウトライン化を選べる。フォントは同梱前提で外部フォント参照を持たない。
<<<
EXAMPLE: <text x="120" y="40" font-size="12">DR1</text>
RELATIONS:
- TYPE: Parent
  VALUE: IO-L1-003
  ROLE: Satisfies

[[/SECTION]]

[[SECTION]]
TITLE: 4. 入力検証・サニタイズ (参照)

[TEXT]
STATEMENT: >>>
JSON / MSPDI XML / SVG / PNG の Import における検証・サニタイズ ( XXE 無効化・ innerHTML
直挿し禁止・スキーマ/型不適合の拒否・ SVG ホワイトリスト無害化 ) は、要求 IO-L1-006 および
コンポーネント ARCH-C-026 ( インポートサニタイザ ) で定義済みである。本書のデータ契約は
検証を通過した後のモデル <-> 形式の対応を定めるものであり、検証仕様をここで再定義しない。
Import されたデータは信頼できない入力として扱う ( 00-overview 前提 )。
<<<

[[/SECTION]]

[[SECTION]]
TITLE: 5. 実装フェーズ橋渡し (次期版スキーマ・コードへの反映)

[TEXT]
STATEMENT: >>>
本節は CR-001 / CR-002 / CR-003 / CR-004 の段階化方針 ( 各 CR §8 ) に基づく実装フェーズ向けの橋渡しである。
本仕様確定フェーズでは現行 SSOT ``docs/api/gr-scheduler.schema.json`` と ``src/**`` を変更しない。
理由は、現行 schema.json が F0 で SSOT 化され ``tests/document-schema-conformance.test.ts`` が
コード出力と突合しているため、コードより先に schema を変更するとテストが赤化するからである。よって
schema とコードは実装セッションで同時に変更し緑を保つ。 CR-001 の目標形状は既に次期版スキーマ
``docs/api/gr-scheduler.schema.next.json`` ( 現物のファイル名は暫定 ``gr-scheduler.schema.h.json``。
承認済みの改称・ CR-002 §3 ) に反映済みであり、これが実装スワップ時に現行
``gr-scheduler.schema.json`` を置き換える権威ある目標形状である。実装は同ファイルを唯一の目標形状
として適用し、本節では旧来のプローズ差分を重複列挙しない ( 具体形状は次期版スキーマを直接参照 )。
<<<

[TEXT]
STATEMENT: >>>
次期版スキーマ ``gr-scheduler.schema.next.json`` へ実装フェーズで加える残差分 ( CR-001 反映済みに
対する CR-002 / CR-003 の増分。詳細形状は同スキーマが SSOT ):

- CR-002 Part 3: ``$defs/item`` から ``previousPlan`` ( および ``$defs/previousPlan`` ) を除去する
  ( ベースラインは別ファイル参照文書へ移行・ DATA-JSON-016 )。
- CR-002 Part 3: MSPDI Baseline を参照文書の id 突合による best-effort 往復へ ( codec 側 )。
- CR-003 Part 2: ``$defs/item.labelPosition`` の enum に ``inner-left`` を追加する
  ( バー内左揃え。 バー外の ``left`` と別値 )。
- CR-004 Part 6c: ``$defs/item.milestoneShape`` の enum に特殊マイルストーン 7 種を追加する。
  暫定英語キー ( 実装セッションで確定 ): ``file`` ( 図面/資料提出 ) / ``box3d`` ( ECU 等の
  ハードウェア成果物 ) / ``floppy`` ( SW リリース ) / ``cylinder`` ( サーバーへの SW デプロイ ) /
  ``person`` ( 偉い人への報告 ) / ``smiley`` ( 楽しいイベント ) / ``beer`` ( 飲み会 )。
  ``taskShape`` enum は対象外 ( 変更なし )。
- CR-004 Part 6b: 既定 ``star`` の描画を塗り潰しから輪郭 ( ☆ ) へ変更する。塗りは ``fillColor``
  依存とし、 enum 値 ``star`` 自体は不変 ( 既定描画状態の変更 )。
- CR-004 Part 6a: ``$defs/item`` から ``importedAssetId`` フィールドを削除し、 JSON/MSPDI
  マッピングから ``assets[]`` 配列 ( ``ImportedAsset`` ) を除去する ( 未公開のため互換不要 )。

併せて更新するコード ( 緑維持のため同一セッションで ):

- ``src/domain/model/schedule-model.ts`` = ``ScheduleItem`` から ``previousPlan`` を除去、
  ``labelPosition`` に ``'inner-left'`` を追加 ( actualStart / actualEnd / targetDate /
  planActualStyle / linkType / lagDays は CR-001 で反映済み )。
- ``src/domain/usecase/json-codec.ts`` = ``previousPlan`` 除去跡の直列化・受理 ( 後方互換不要、
  各 CR §4 )。
- ``src/domain/usecase/mspdi-codec.ts`` = Baseline best-effort ( id 突合 )、 Deadline /
  linkType / lagDays の Export/Import ( 本書 §2 DATA-MSPDI-003/004/007/008/009 )。
- ``src/domain/usecase/plan-actual-colors.ts`` = fillColor からの彩度導出 ( 予定=淡 / 実績=濃 )
  ＋線幅 ( 予定=細 / 実績=太 ) 方式へ作り替え ( CR-002 Part 1、 PLAN-L1-005 )。
- ベースライン参照ローダ / グレー・アンダーレイ描画層 ( 新規・読取専用 ) = 別ファイル読込 ＋
  id 突合 ＋ 同高さグレー描画 ( CR-002 Part 3、 PLAN-L1-004 )。
- ``src/adapters/render/layers/item-layer.ts`` = マイルストーン 2 マーカー ( 塗り無し ) 描画
  ( CR-002 Part 2 )。
- ``src/adapters/render/layers/progress-today-layer.ts`` = 統一 front 規則 ＋ マイルストーン特例
  ( 点・補間しない・ PLAN-L2-001、 CR-002 Part 2 )。
- ヘッダー / ツールバー ＋ 依存線ルータ = CR-003 Part 1 / Part 3 ( ヘッダー再編・テーマ 4 種・
  決定的直交配線 )。
- ``src/domain/model/schedule-model.ts`` = ``importedAssetId`` の除去、 ``milestoneShape`` enum の
  特殊 7 種拡張、 ``ImportedAsset`` 型と ``assets[]`` の削除 ( CR-004 Part 6a/6c )。
- ``src/adapters/render/layers/item-layer.ts`` ＋ パレット UI = ``star`` の輪郭描画、特殊
  マイルストーン 7 種の SVG 描画とパレット [...] 展開、マイルストーン寸法 +15% とラベルフォントの
  マイルストーンアイコン基準算出、担当者名レイアウト ( CR-004 Part 2 / 5 / 6b / 6c )。
- ``src/domain/usecase/import-sanitizer.ts`` ＋ ``src/adapters/io/import-service.ts`` = 画像
  ( SVG/PNG ) インポート経路の撤去 ( CR-004 Part 6a、 ARCH-C-026 )。
- レイアウトエンジン ( ``src/domain/usecase/layout-engine.ts`` 等 ) = サブレーン割当順の下から
  上への反転、フォント大時のセクション行マージン算出 ( CR-004 Part 1 / 3、 ALIGN-L2-004 /
  ALIGN-L2-005 )。
- プロパティパネル = ``end_date`` / ``fade_in_days`` / ``fade_out_days`` / ``actual_end`` の
  ラベル右詰め・値入力左揃え統一 ( CR-004 Part 4、 PROP-L2-001 )。
- ``src/app/sample-data.ts`` とフィクスチャ = 上記新形状へ更新。
- ``tests/document-schema-conformance.test.ts`` は次期版スキーマとコード出力を同時に切替えて
  緑を保つ ( 本節の残差分を 1 セッションで適用する )。
<<<

[[/SECTION]]
